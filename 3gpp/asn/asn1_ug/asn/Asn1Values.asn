-- https://www.erlang.org/doc/apps/asn1/asn1_getting_started.html#asn-1-values

Asn1Values DEFINITIONS AUTOMATIC TAGS ::=
BEGIN

/* Values can be assigned to an ASN.1 type within the ASN.1 code itself,
   as opposed to the actions in the previous section where a value was assigned to an ASN.1 type in Erlang.
   The full value syntax of ASN.1 is supported and X.680 describes in detail how to assign values in ASN.1.
   A short example:
*/

TT ::= SEQUENCE {
   a INTEGER,
   b SET OF IA5String } -- WAS: OCTET STRING, changed due to reported error (below)

tt TT ::= {a 77,b {"kalle","kula"}}
--                 ^ error A0120E: Parsing error: expecting a bstring, or an hstring but found CSTRING.

/* The value defined here can be used in several ways.
   It can, for example, be used as the value in some DEFAULT component:
*/

SS ::= SET {
    s OBJECT IDENTIFIER,
    val TT DEFAULT tt }

/* It can also be used from inside an Erlang program. If this ASN.1 code is defined in ASN.1 module Values,
   the ASN.1 value tt can be reached from Erlang as a function call to 'Values':tt() as in the following example:

1> Val = 'Values':tt().
{'TT',77,["kalle","kula"]}

2> {ok,Bytes} = 'Values':encode('TT',Val).
{ok,<<48,18,128,1,77,161,13,4,5,107,97,108,108,101,4,4,
      107,117,108,97>>}

3> 'Values':decode('TT',Bytes).
{ok,{'TT',77,["kalle","kula"]}}

This example shows that a function is generated by the compiler that returns a valid Erlang representation of the value,
although the value is of a complex type.
Furthermore, if the option maps is not used, a macro is generated for each value in the .hrl file. So,
the defined value tt can also be extracted by ?tt in application code.

*/

END
