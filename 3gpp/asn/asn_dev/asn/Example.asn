Example DEFINITIONS AUTOMATIC TAGS ::=
BEGIN

-- [3.6 Naming of Records in .hrl Files](http://erlang.org/doc/apps/asn1/asn1_getting_started.html#naming-of-records-in-.hrl-files)

-- -record('Rec1_a_b',{c}).

Rec1 ::= SEQUENCE {
    a CHOICE {
        b SEQUENCE {
            c INTEGER
        }
    }
}

-- -record('Rec2_a_SEQOF'{b}).
-- -record('Rec2_c_SETOF'{d}).

Rec2 ::= SEQUENCE {
    a SEQUENCE OF SEQUENCE {
        b BOOLEAN
    },
    c SET OF SEQUENCE {
        d INTEGER
    }
}

Def3 ::= Rec3

Rec3 ::= SEQUENCE {
    a SEQUENCE {
        b SEQUENCE {
            c SEQUENCE {
                x INTEGER,
                y INTEGER
            }
        }
    },
    ...,
    d INTEGER
}

WeekDay ::= ENUMERATED { mon(1), tue(2), wed(3), thu(4), fri(5), sat(6), sun(7) }

Dim3 ::= SEQUENCE OF SEQUENCE OF SEQUENCE OF CHOICE {
    pnt SEQUENCE {
        x INTEGER,
        y INTEGER
    },
    vec Vec,
    day WeekDay,
    rem Telework
}

Vec ::= SEQUENCE {
    x INTEGER,
    y INTEGER
}

Telework ::= SEQUENCE OF WeekDay

-- [3.9 ASN.1 Information Objects (X.681)](http://erlang.org/doc/apps/asn1/asn1_getting_started.html#macros)

--  Information Object Class

GENERAL-PROCEDURE ::= CLASS {
    &Message,
    &Reply          OPTIONAL,
    &Error          OPTIONAL,
    &id         PrintableString UNIQUE
}
WITH SYNTAX {
    NEW MESSAGE     &Message
    [REPLY          &Reply]
    [ERROR          &Error]
    ADDRESS         &id
}

-- Objects

object1 GENERAL-PROCEDURE ::= {
    NEW MESSAGE     PrintableString
    ADDRESS         "home"
}

object2 GENERAL-PROCEDURE ::= {
    NEW MESSAGE     INTEGER
    ERROR           INTEGER
    ADDRESS         "remote"
}

-- Object set

GENERAL-PROCEDURES GENERAL-PROCEDURE ::= {
    object1 | object2, ...}

--

StartMessage  ::= SEQUENCE {
    msgId   GENERAL-PROCEDURE.&id       ({GENERAL-PROCEDURES}),
    content GENERAL-PROCEDURE.&Message  ({GENERAL-PROCEDURES}{@msgId})
}

END
