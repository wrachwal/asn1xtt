NBIOT-RRC-Definitions DEFINITIONS AUTOMATIC TAGS ::=

BEGIN

IMPORTS
    RRCConnectionReestablishmentReject,
    SecurityModeCommand,
    SecurityModeComplete,
    SecurityModeFailure,
    AdditionalSpectrumEmission,
    ARFCN-ValueEUTRA-r9,
    CarrierFreqsGERAN,
    CellGlobalIdEUTRA,
    CellIdentity,
    C-RNTI,
    DedicatedInfoNAS,
    DRB-Identity,
    GNSS-PositionFixDuration-r18,
    GNSS-ValidityDuration-r17,
    InitialUE-Identity,
    IntraFreqExcludedCellList,
    IntraFreqNeighCellList,
    I-RNTI-r15,
    LocationInfo-r10,
    maxAccessCat-1-r15,
    maxBands,
    maxExcludedCell,
    maxCellInter,
    maxCellIntra,
    maxFBI2,
    maxFreq,
    maxMultiBands,
    maxNrofS-NSSAI-r15,
    maxPageRec,
    maxPLMN-r11,
    maxSAI-MBMS-r11,
    maxSat-r17,
    maxSIB,
    maxSIB-1,
    MBMS-SAI-r11,
    MBMS-SAI-List-r11,
    MBMSSessionInfo-r13,
    NeighSatelliteInfoList-r18,
    NextHopChainingCount,
    NG-5G-S-TMSI-r15,
    PagingUE-Identity,
    PLMN-Identity,
    PLMN-IdentityList2,
    P-Max,
    PowerRampingParameters,
    PreambleTransMax,
    PhysCellId,
    Q-OffsetRange,
    Q-QualMin-r9,
    Q-RxLevMin,
    ReestabUE-Identity,
    RegisteredAMF-r15,
    RegisteredMME,
    ReselectionThreshold,
    ResumeIdentity-r13,
    RRC-TransactionIdentifier,
    RSRP-Range,
    S-NSSAI-r15,
    S-TMSI,
    SatelliteId-r18,
    SatelliteInfoList-r17,
    SatelliteInfoList-v1800,
    ServingSatelliteInfo-r17,
    SetupRelease,
    ShortMAC-I,
    SystemInformationBlockType16-r11,
    SystemInfoValueTagSI-r13,
    T-Reordering,
    T-ReorderingExt-r17,
    TimeAlignmentTimer,
    TimeSinceFailure-r11,
    TimeOffsetUTC-r17,
    TMGI-r9,
    TrackingAreaCode,
    TrackingAreaCode-5GC-r15,
    UAC-AC1-SelectAssistInfo-r15,
    DataInactivityTimer-r14

FROM EUTRA-RRC-Definitions;

BCCH-BCH-Message-NB ::= SEQUENCE {
    message                 BCCH-BCH-MessageType-NB
}


BCCH-BCH-MessageType-NB::=  MasterInformationBlock-NB


BCCH-BCH-Message-TDD-NB ::= SEQUENCE {
    message                 BCCH-BCH-MessageType-TDD-NB-r15
}


BCCH-BCH-MessageType-TDD-NB-r15 ::= MasterInformationBlock-TDD-NB-r15

BCCH-DL-SCH-Message-NB ::= SEQUENCE {
    message                 BCCH-DL-SCH-MessageType-NB
}

BCCH-DL-SCH-MessageType-NB ::= CHOICE {
    c1                      CHOICE {
        systemInformation-r13               SystemInformation-NB,
        systemInformationBlockType1-r13     SystemInformationBlockType1-NB
    },
    messageClassExtension   SEQUENCE {}
}

PCCH-Message-NB ::= SEQUENCE {
    message                 PCCH-MessageType-NB
}

PCCH-MessageType-NB ::= CHOICE {
    c1                      CHOICE {
        paging-r13                          Paging-NB
    },
    messageClassExtension   SEQUENCE {}
}

DL-CCCH-Message-NB ::= SEQUENCE {
    message                 DL-CCCH-MessageType-NB
}

DL-CCCH-MessageType-NB ::= CHOICE {
    c1                      CHOICE {
        rrcConnectionReestablishment-r13        RRCConnectionReestablishment-NB,
        rrcConnectionReestablishmentReject-r13  RRCConnectionReestablishmentReject,
        rrcConnectionReject-r13                 RRCConnectionReject-NB,
        rrcConnectionSetup-r13                  RRCConnectionSetup-NB,
        rrcEarlyDataComplete-r15                RRCEarlyDataComplete-NB-r15,
        spare3 NULL, spare2 NULL, spare1 NULL
    },
    messageClassExtension   SEQUENCE {}
}

DL-DCCH-Message-NB ::= SEQUENCE {
    message                 DL-DCCH-MessageType-NB
}

DL-DCCH-MessageType-NB ::= CHOICE {
    c1                      CHOICE {
        dlInformationTransfer-r13               DLInformationTransfer-NB,
        rrcConnectionReconfiguration-r13        RRCConnectionReconfiguration-NB,
        rrcConnectionRelease-r13                RRCConnectionRelease-NB,
        securityModeCommand-r13                 SecurityModeCommand,
        ueCapabilityEnquiry-r13                 UECapabilityEnquiry-NB,
        rrcConnectionResume-r13                 RRCConnectionResume-NB,
        ueInformationRequest-r16                UEInformationRequest-NB-r16,
        spare1 NULL
    },
    messageClassExtension   SEQUENCE {}
}


UL-CCCH-Message-NB ::= SEQUENCE {
    message                 UL-CCCH-MessageType-NB
}

UL-CCCH-MessageType-NB ::= CHOICE {
    c1                      CHOICE {
        rrcConnectionReestablishmentRequest-r13 RRCConnectionReestablishmentRequest-NB,
        rrcConnectionRequest-r13                RRCConnectionRequest-NB,
        rrcConnectionResumeRequest-r13          RRCConnectionResumeRequest-NB,
        rrcEarlyDataRequest-r15             RRCEarlyDataRequest-NB-r15
    },
    messageClassExtension   SEQUENCE {}
}

SC-MCCH-Message-NB ::= SEQUENCE {
    message                 SC-MCCH-MessageType-NB
}


SC-MCCH-MessageType-NB ::= CHOICE {
    c1                      CHOICE {
        scptmConfiguration-r14                      SCPTMConfiguration-NB-r14
    },
    messageClassExtension   SEQUENCE {}
}

UL-DCCH-Message-NB ::= SEQUENCE {
    message                 UL-DCCH-MessageType-NB
}

UL-DCCH-MessageType-NB ::= CHOICE {
    c1                      CHOICE {
        rrcConnectionReconfigurationComplete-r13    RRCConnectionReconfigurationComplete-NB,
        rrcConnectionReestablishmentComplete-r13    RRCConnectionReestablishmentComplete-NB,
        rrcConnectionSetupComplete-r13              RRCConnectionSetupComplete-NB,
        securityModeComplete-r13                    SecurityModeComplete,
        securityModeFailure-r13                     SecurityModeFailure,
        ueCapabilityInformation-r13                 UECapabilityInformation-NB,
        ulInformationTransfer-r13                   ULInformationTransfer-NB,
        rrcConnectionResumeComplete-r13             RRCConnectionResumeComplete-NB,
        ueInformationResponse-r16                   UEInformationResponse-NB-r16,
        purConfigurationRequest-r16                 PURConfigurationRequest-NB-r16,
        spare6 NULL, spare5 NULL, spare4 NULL,
        spare3 NULL, spare2 NULL, spare1 NULL
    },
    messageClassExtension   SEQUENCE {}
}

DLInformationTransfer-NB ::=    SEQUENCE {
    rrc-TransactionIdentifier           RRC-TransactionIdentifier,
    criticalExtensions                  CHOICE {
        c1                                  CHOICE {
            dlInformationTransfer-r13       DLInformationTransfer-NB-r13-IEs,
            spare1 NULL
        },
        criticalExtensionsFuture            SEQUENCE {}
    }
}

DLInformationTransfer-NB-r13-IEs ::=    SEQUENCE {
    dedicatedInfoNAS-r13                    DedicatedInfoNAS,
    lateNonCriticalExtension                OCTET STRING                    OPTIONAL,
    nonCriticalExtension                    SEQUENCE {}                     OPTIONAL
}

MasterInformationBlock-NB ::=   SEQUENCE {
    systemFrameNumber-MSB-r13       BIT STRING (SIZE (4)),
    hyperSFN-LSB-r13                BIT STRING (SIZE (2)),
    schedulingInfoSIB1-r13          INTEGER (0..15),
    systemInfoValueTag-r13          INTEGER (0..31),
    ab-Enabled-r13                  BOOLEAN,
    operationModeInfo-r13           CHOICE {
        inband-SamePCI-r13              Inband-SamePCI-NB-r13,
        inband-DifferentPCI-r13         Inband-DifferentPCI-NB-r13,
        guardband-r13                   Guardband-NB-r13,
        standalone-r13                  Standalone-NB-r13
    },
    additionalTransmissionSIB1-r15  BOOLEAN,
    ab-Enabled-5GC-r16              BOOLEAN,
    partEARFCN-r17                  CHOICE {
        spare                           BIT STRING (SIZE (2)),
        earfcn-LSB                      BIT STRING (SIZE (2))
    },
    spare                           BIT STRING (SIZE (6))
}

Guardband-NB-r13 ::=            SEQUENCE {
    rasterOffset-r13                ChannelRasterOffset-NB-r13,
    spare                           BIT STRING (SIZE (3))
}

Inband-SamePCI-NB-r13 ::=       SEQUENCE {
    eutra-CRS-SequenceInfo-r13      INTEGER (0..31)
}

Inband-DifferentPCI-NB-r13 ::=  SEQUENCE {
    eutra-NumCRS-Ports-r13          ENUMERATED {same, four},
    rasterOffset-r13                ChannelRasterOffset-NB-r13,
    spare                           BIT STRING (SIZE (2))
}

Standalone-NB-r13 ::=           SEQUENCE {
    spare                           BIT STRING (SIZE (5))
}

MasterInformationBlock-TDD-NB-r15 ::=   SEQUENCE {
    systemFrameNumber-MSB-r15               BIT STRING (SIZE (4)),
    hyperSFN-LSB-r15                        BIT STRING (SIZE (2)),
    schedulingInfoSIB1-r15                  INTEGER (0..15),
    systemInfoValueTag-r15                  INTEGER (0..31),
    ab-Enabled-r15                          BOOLEAN,
    operationModeInfo-r15               CHOICE {
        inband-SamePCI-r15                  Inband-SamePCI-TDD-NB-r15,
        inband-DifferentPCI-r15             Inband-DifferentPCI-TDD-NB-r15,
        guardband-r15                       GuardbandTDD-NB-r15,
        standalone-r15                      StandaloneTDD-NB-r15
    },
    sib1-CarrierInfo-r15                    ENUMERATED {anchor, non-anchor},
    ab-Enabled-5GC-r16                      BOOLEAN,
    spare                                   BIT STRING (SIZE (8))
}

GuardbandTDD-NB-r15 ::=             SEQUENCE {
    rasterOffset-r15                    ChannelRasterOffset-NB-r13,
    sib-GuardbandInfo-r15               CHOICE {
        sib-GuardbandAnchor-r15             SIB-GuardbandAnchorTDD-NB-r15,
        sib-GuardbandGuardband-r15          SIB-GuardbandGuardbandTDD-NB-r15,
        sib-GuardbandInbandSamePCI-r15      SIB-GuardbandInbandSamePCI-TDD-NB-r15,
        sib-GuardbandinbandDiffPCI-r15      SIB-GuardbandInbandDiffPCI-TDD-NB-r15
    },
    eutra-Bandwitdh-r15                 ENUMERATED {bw5or10, bw15or20}
}

Inband-SamePCI-TDD-NB-r15 ::=       SEQUENCE {
    eutra-CRS-SequenceInfo-r15          INTEGER (0..31),
    sib-InbandLocation-r15              ENUMERATED {lower, higher}
}

Inband-DifferentPCI-TDD-NB-r15 ::=      SEQUENCE {
    eutra-NumCRS-Ports-r15                  ENUMERATED {same, four},
    rasterOffset-r15                        ChannelRasterOffset-NB-r13,
    sib-InbandLocation-r15                  ENUMERATED {lower, higher},
    spare                                   BIT STRING (SIZE (2))
}

StandaloneTDD-NB-r15 ::=                SEQUENCE {
    sib-StandaloneLocation-r15              ENUMERATED {lower, higher},
    spare                                   BIT STRING (SIZE (5))
}

SIB-GuardbandAnchorTDD-NB-r15 ::=       SEQUENCE {
    spare                                   BIT STRING (SIZE (1))
}

SIB-GuardbandGuardbandTDD-NB-r15 ::=    SEQUENCE {
    sib-GuardbandGuardbandLocation-r15      ENUMERATED {same, opposite}
}

SIB-GuardbandInbandSamePCI-TDD-NB-r15 ::= SEQUENCE {
    spare                                   BIT STRING (SIZE (1))
}

SIB-GuardbandInbandDiffPCI-TDD-NB-r15 ::= SEQUENCE {
    sib-EUTRA-NumCRS-Ports-r15              ENUMERATED {same, four}
}

Paging-NB ::=                       SEQUENCE {
    pagingRecordList-r13                PagingRecordList-NB-r13     OPTIONAL,   -- Need ON
    systemInfoModification-r13          ENUMERATED {true}               OPTIONAL,   -- Need ON
    systemInfoModification-eDRX-r13     ENUMERATED {true}               OPTIONAL,   -- Need ON
    nonCriticalExtension                Paging-NB-v1610-IEs             OPTIONAL
}

Paging-NB-v1610-IEs ::=             SEQUENCE {
    pagingRecordList-v1610              PagingRecordList-NB-v1610       OPTIONAL,   -- Need ON
    nonCriticalExtension                SEQUENCE {}                     OPTIONAL
}

PagingRecordList-NB-r13 ::=         SEQUENCE (SIZE (1..maxPageRec)) OF PagingRecord-NB-r13

PagingRecordList-NB-v1610 ::=       SEQUENCE (SIZE (1..maxPageRec)) OF PagingRecord-NB-v1610

PagingRecord-NB-r13 ::=             SEQUENCE {
    ue-Identity-r13                     PagingUE-Identity,
    ...
}

PagingRecord-NB-v1610 ::=           SEQUENCE {
    mt-EDT-r16                          ENUMERATED {true}           OPTIONAL    -- Need ON
}

PURConfigurationRequest-NB-r16 ::=  SEQUENCE {
    criticalExtensions                  CHOICE {
        purConfigurationRequest-r16         PURConfigurationRequest-NB-r16-IEs,
        criticalExtensionsFuture            SEQUENCE {}
    }
}

PURConfigurationRequest-NB-r16-IEs ::=  SEQUENCE {
    pur-ConfigRequest-r16                   PUR-ConfigRequest-NB-r16            OPTIONAL,
    lateNonCriticalExtension                OCTET STRING                        OPTIONAL,
    nonCriticalExtension                    SEQUENCE {}                         OPTIONAL
}

PUR-ConfigRequest-NB-r16 ::=        CHOICE{
    pur-ReleaseRequest                  NULL,
    pur-SetupRequest                    SEQUENCE {
        requestedNumOccasions-r16           ENUMERATED {one, infinite},
        requestedPeriodicityAndOffset-r16   PUR-PeriodicityAndOffset-NB-r16,
        requestedTBS-r16                    ENUMERATED {b328, b376, b424, b472, b504, b552, b584,
                                                        b616, b680, b744, b776, b808, b872, b904,
                                                        b936, b968, b1000, b1032, b1096, b1128,
                                                        b1192, b1224, b1256, b1352, b1384, b1544,
                                                        b1608, b1736, b1800, b2024, b2280, b2536},
        rrc-ACK-r16                         ENUMERATED {true}                   OPTIONAL
    }
}

RRCConnectionReconfiguration-NB ::= SEQUENCE {
    rrc-TransactionIdentifier               RRC-TransactionIdentifier,
    criticalExtensions                      CHOICE {
        c1                                      CHOICE{
            rrcConnectionReconfiguration-r13        RRCConnectionReconfiguration-NB-r13-IEs,
            spare1 NULL
        },
        criticalExtensionsFuture            SEQUENCE {}
    }
}

RRCConnectionReconfiguration-NB-r13-IEs ::= SEQUENCE {
    dedicatedInfoNASList-r13            SEQUENCE (SIZE(1..maxDRB-NB-r13)) OF
                                                    DedicatedInfoNAS        OPTIONAL,   -- Need ON
    radioResourceConfigDedicated-r13    RadioResourceConfigDedicated-NB-r13 OPTIONAL,   -- Need ON
    fullConfig-r13                      ENUMERATED {true}                   OPTIONAL,   -- Cond Reestab
    lateNonCriticalExtension            OCTET STRING                        OPTIONAL,
    nonCriticalExtension                RRCConnectionReconfiguration-NB-v16f0-IEs   OPTIONAL
}

RRCConnectionReconfiguration-NB-v16f0-IEs ::=       SEQUENCE {
    obtainLocationNB-r16            ENUMERATED {setup}                      OPTIONAL,   -- Need OR
    nonCriticalExtension                SEQUENCE {}                         OPTIONAL
}

RRCConnectionReconfigurationComplete-NB ::= SEQUENCE {
    rrc-TransactionIdentifier               RRC-TransactionIdentifier,
    criticalExtensions                      CHOICE {
        rrcConnectionReconfigurationComplete-r13    RRCConnectionReconfigurationComplete-NB-r13-IEs,
        criticalExtensionsFuture                    SEQUENCE {}
    }
}

RRCConnectionReconfigurationComplete-NB-r13-IEs ::= SEQUENCE {
    lateNonCriticalExtension            OCTET STRING                    OPTIONAL,
    nonCriticalExtension                SEQUENCE {}                     OPTIONAL
}


RRCConnectionReestablishment-NB ::= SEQUENCE {
    rrc-TransactionIdentifier           RRC-TransactionIdentifier,
    criticalExtensions                  CHOICE {
        c1                                  CHOICE{
            rrcConnectionReestablishment-r13    RRCConnectionReestablishment-NB-r13-IEs,
            spare1  NULL
        },
        criticalExtensionsFuture            SEQUENCE {}
    }
}

RRCConnectionReestablishment-NB-r13-IEs ::= SEQUENCE {
    radioResourceConfigDedicated-r13            RadioResourceConfigDedicated-NB-r13,
    nextHopChainingCount-r13                    NextHopChainingCount,
    lateNonCriticalExtension                    OCTET STRING                        OPTIONAL,
    nonCriticalExtension                        RRCConnectionReestablishment-NB-v1430-IEs   OPTIONAL
}

RRCConnectionReestablishment-NB-v1430-IEs ::=   SEQUENCE {
    dl-NAS-MAC                          BIT STRING (SIZE (16))  OPTIONAL,   -- Cond Reestablish-CP
    nonCriticalExtension                SEQUENCE {}             OPTIONAL
}

RRCConnectionReestablishmentComplete-NB ::= SEQUENCE {
    rrc-TransactionIdentifier               RRC-TransactionIdentifier,
    criticalExtensions                      CHOICE {
        rrcConnectionReestablishmentComplete-r13    RRCConnectionReestablishmentComplete-NB-r13-IEs,
        criticalExtensionsFuture                    SEQUENCE {}
    }
}

RRCConnectionReestablishmentComplete-NB-r13-IEs ::= SEQUENCE {
    lateNonCriticalExtension            OCTET STRING                    OPTIONAL,
    nonCriticalExtension                RRCConnectionReestablishmentComplete-NB-v1470-IEs   OPTIONAL
}

RRCConnectionReestablishmentComplete-NB-v1470-IEs ::= SEQUENCE {
    measResultServCell-r14          MeasResultServCell-NB-r14       OPTIONAL,
    nonCriticalExtension            RRCConnectionReestablishmentComplete-NB-v1610-IEs   OPTIONAL
}

RRCConnectionReestablishmentComplete-NB-v1610-IEs ::= SEQUENCE {
    rlf-InfoAvailable-r16               ENUMERATED {true}               OPTIONAL,
    anr-InfoAvailable-r16               ENUMERATED {true}               OPTIONAL,
    nonCriticalExtension                RRCConnectionReestablishmentComplete-NB-v1710-IEs   OPTIONAL
}

RRCConnectionReestablishmentComplete-NB-v1710-IEs ::= SEQUENCE {
    gnss-ValidityDuration-r17           GNSS-ValidityDuration-r17       OPTIONAL,
    nonCriticalExtension                RRCConnectionReestablishmentComplete-NB-v1800-IEs       OPTIONAL
}

RRCConnectionReestablishmentComplete-NB-v1800-IEs ::= SEQUENCE {
    gnss-PositionFixDuration-r18        GNSS-PositionFixDuration-r18    OPTIONAL,
    nonCriticalExtension                SEQUENCE {}                     OPTIONAL
}

RRCConnectionReestablishmentRequest-NB ::= SEQUENCE {
    criticalExtensions                  CHOICE {
        rrcConnectionReestablishmentRequest-r13
                                            RRCConnectionReestablishmentRequest-NB-r13-IEs,
        later                               CHOICE {
            rrcConnectionReestablishmentRequest-r14
                                            RRCConnectionReestablishmentRequest-NB-r14-IEs,
            later                           CHOICE {
                rrcConnectionReestablishmentRequest-r16
                                            RRCConnectionReestablishmentRequest-5GC-NB-r16-IEs,
                criticalExtensionsFuture    SEQUENCE {}
            }
        }
    }
}

RRCConnectionReestablishmentRequest-NB-r13-IEs ::= SEQUENCE {
    ue-Identity-r13                     ReestabUE-Identity,
    reestablishmentCause-r13            ReestablishmentCause-NB-r13,
    cqi-NPDCCH-r14                      CQI-NPDCCH-NB-r14,
    earlyContentionResolution-r14       BOOLEAN,
    spare                               BIT STRING (SIZE (20))
}

RRCConnectionReestablishmentRequest-NB-r14-IEs ::= SEQUENCE {
    ue-Identity-r14                     ReestabUE-Identity-CP-NB-r14,
    reestablishmentCause-r14            ReestablishmentCause-NB-r13,
    cqi-NPDCCH-r14                      CQI-NPDCCH-Short-NB-r14,
    earlyContentionResolution-r14       BOOLEAN,
    spare                               BIT STRING (SIZE (1))
}

RRCConnectionReestablishmentRequest-5GC-NB-r16-IEs ::= SEQUENCE {
    ue-Identity-r16                     ReestabUE-Identity-CP-5GC-NB-r16,
    reestablishmentCause-r16            ReestablishmentCause-NB-r13,
    cqi-NPDCCH-r16                      CQI-NPDCCH-Short-NB-r14,
    spare                               BIT STRING (SIZE (1))
}

ReestablishmentCause-NB-r13 ::=         ENUMERATED {
                                            reconfigurationFailure, otherFailure,
                                            spare2, spare1}

ReestabUE-Identity-CP-NB-r14 ::=        SEQUENCE {
    s-TMSI-r14                              S-TMSI,
    ul-NAS-MAC-r14                          BIT STRING (SIZE (16)),
    ul-NAS-Count-r14                        BIT STRING (SIZE (5))
}

ReestabUE-Identity-CP-5GC-NB-r16 ::=    SEQUENCE {
    truncated5G-S-TMSI-r16                  BIT STRING (SIZE (40)),
    ul-NAS-MAC-r16                          BIT STRING (SIZE (16)),
    ul-NAS-Count-r16                        BIT STRING (SIZE (5))
}

RRCConnectionReject-NB ::=              SEQUENCE {
    criticalExtensions                  CHOICE {
        c1                                  CHOICE {
            rrcConnectionReject-r13             RRCConnectionReject-NB-r13-IEs,
            spare1 NULL
        },
        criticalExtensionsFuture            SEQUENCE {}
    }
}

RRCConnectionReject-NB-r13-IEs ::=      SEQUENCE {
    extendedWaitTime-r13                    INTEGER (1..1800),
    rrc-SuspendIndication-r13               ENUMERATED {true}           OPTIONAL,   -- Need ON
    lateNonCriticalExtension                OCTET STRING                OPTIONAL,
    nonCriticalExtension                    SEQUENCE {}                 OPTIONAL
}

RRCConnectionRelease-NB ::=     SEQUENCE {
    rrc-TransactionIdentifier           RRC-TransactionIdentifier,
    criticalExtensions                  CHOICE {
        c1                                  CHOICE {
            rrcConnectionRelease-r13            RRCConnectionRelease-NB-r13-IEs,
            spare1 NULL
        },
        criticalExtensionsFuture            SEQUENCE {}
    }
}

RRCConnectionRelease-NB-r13-IEs ::= SEQUENCE {
    releaseCause-r13                    ReleaseCause-NB-r13,
    resumeIdentity-r13                  ResumeIdentity-r13              OPTIONAL,   -- Need OR
    extendedWaitTime-r13                INTEGER (1..1800)               OPTIONAL,   -- Need ON
    redirectedCarrierInfo-r13           RedirectedCarrierInfo-NB-r13    OPTIONAL,   -- Need ON
    lateNonCriticalExtension            OCTET STRING                    OPTIONAL,
    nonCriticalExtension                RRCConnectionRelease-NB-v1430-IEs       OPTIONAL
}

RRCConnectionRelease-NB-v1430-IEs ::=   SEQUENCE {
    redirectedCarrierInfo-v1430         RedirectedCarrierInfo-NB-v1430  OPTIONAL,   -- Cond Redirection
    extendedWaitTime-CPdata-r14     INTEGER (1..1800)   OPTIONAL,   -- Cond NoExtendedWaitTime
    nonCriticalExtension                RRCConnectionRelease-NB-v1530-IEs   OPTIONAL
}

RRCConnectionRelease-NB-v1530-IEs ::=   SEQUENCE {
    drb-ContinueROHC-r15                    ENUMERATED {true}           OPTIONAL,   -- Cond UP-EDT
    nextHopChainingCount-r15                NextHopChainingCount        OPTIONAL,   -- Cond EarlySec
    nonCriticalExtension                RRCConnectionRelease-NB-v1550-IEs   OPTIONAL
}

RRCConnectionRelease-NB-v1550-IEs ::=   SEQUENCE {
    redirectedCarrierInfo-v1550         RedirectedCarrierInfo-NB-v1550  OPTIONAL,   -- Cond Redirection-TDD
    nonCriticalExtension                RRCConnectionRelease-NB-v15b0-IEs   OPTIONAL
}

RRCConnectionRelease-NB-v15b0-IEs ::=   SEQUENCE {
    noLastCellUpdate-r15                    ENUMERATED {true}       OPTIONAL,   -- Need OP
    nonCriticalExtension                    RRCConnectionRelease-NB-v1610-IEs       OPTIONAL
}

RRCConnectionRelease-NB-v1610-IEs ::=   SEQUENCE {
    resumeIdentity-r16                      I-RNTI-r15                  OPTIONAL,   -- Need OR
    anr-MeasConfig-r16                      ANR-MeasConfig-NB-r16       OPTIONAL,   -- Need OP
    pur-Config-r16                          SetupRelease {PUR-Config-NB-r16}
                                                                        OPTIONAL,   -- Need ON
    nonCriticalExtension                    RRCConnectionRelease-NB-v1700-IEs   OPTIONAL
}

RRCConnectionRelease-NB-v1700-IEs ::=   SEQUENCE {
    cbp-Index-r17           INTEGER (1..2)              OPTIONAL,   -- Need OR
    nonCriticalExtension    SEQUENCE {}             OPTIONAL
}

ReleaseCause-NB-r13 ::=                 ENUMERATED {loadBalancingTAUrequired, other,
                                                    rrc-Suspend, spare1}
RedirectedCarrierInfo-NB-r13::=         CarrierFreq-NB-r13

RedirectedCarrierInfo-NB-v1430  ::=     SEQUENCE {
    redirectedCarrierOffsetDedicated-r14    ENUMERATED{
                                                dB1, dB2, dB3, dB4, dB5, dB6, dB8, dB10,
                                                dB12, dB14, dB16, dB18, dB20, dB22, dB24, dB26},
    t322-r14                                ENUMERATED{
                                                min5, min10, min20, min30, min60, min120, min180,
                                                spare1}
}

RedirectedCarrierInfo-NB-v1550::=       CarrierFreq-NB-v1550

RRCConnectionRequest-NB ::=     SEQUENCE {
    criticalExtensions                  CHOICE {
        rrcConnectionRequest-r13            RRCConnectionRequest-NB-r13-IEs,
        later                               CHOICE {
            rrcConnectionRequest-r16            RRCConnectionRequest-5GC-NB-r16-IEs,
            criticalExtensionsFuture            SEQUENCE {}
        }
    }
}

RRCConnectionRequest-NB-r13-IEs ::=     SEQUENCE {
    ue-Identity-r13                         InitialUE-Identity,
    establishmentCause-r13                  EstablishmentCause-NB-r13,
    multiToneSupport-r13                    ENUMERATED {true}               OPTIONAL,
    multiCarrierSupport-r13                 ENUMERATED {true}               OPTIONAL,
    earlyContentionResolution-r14           BOOLEAN,
    cqi-NPDCCH-r14                          CQI-NPDCCH-NB-r14,
    spare                                   BIT STRING (SIZE (17))
}

RRCConnectionRequest-5GC-NB-r16-IEs ::= SEQUENCE {
    ue-Identity-r16                         InitialUE-Identity-5GC-NB-r16,
    establishmentCause-r16                  ENUMERATED {
                                                mt-Access, mo-Signalling, mo-Data, mo-ExceptionData,
                                                spare4, spare3, spare2, spare1},
    cqi-NPDCCH-r16                          CQI-NPDCCH-NB-r14,
    spare                                   BIT STRING (SIZE (11))
}

InitialUE-Identity-5GC-NB-r16 ::=       CHOICE {
    ng-5G-S-TMSI-r16                        NG-5G-S-TMSI-r15,
    randomValue                             BIT STRING (SIZE (48))
}

RRCConnectionResume-NB ::=      SEQUENCE {
    rrc-TransactionIdentifier           RRC-TransactionIdentifier,
    criticalExtensions                  CHOICE {
        c1                                  CHOICE {
            rrcConnectionResume-r13             RRCConnectionResume-NB-r13-IEs,
            spare1                              NULL
        },
        criticalExtensionsFuture            SEQUENCE {}
    }
}

RRCConnectionResume-NB-r13-IEs ::=      SEQUENCE {
    radioResourceConfigDedicated-r13        RadioResourceConfigDedicated-NB-r13 OPTIONAL,       -- Need ON
    nextHopChainingCount-r13                NextHopChainingCount,
    drb-ContinueROHC-r13                    ENUMERATED {true}               OPTIONAL,   -- Need OP
    lateNonCriticalExtension                OCTET STRING                    OPTIONAL,
    nonCriticalExtension                    RRCConnectionResume-NB-v1610-IEs    OPTIONAL
}

RRCConnectionResume-NB-v1610-IEs ::=    SEQUENCE {
    fullConfig-r16                          ENUMERATED {true}       OPTIONAL,   -- Cond 5GC
    nonCriticalExtension                    RRCConnectionResume-NB-v16f0-IEs                OPTIONAL
}

RRCConnectionResume-NB-v16f0-IEs ::=    SEQUENCE {
    obtainLocationNB-r16                    ENUMERATED {setup}      OPTIONAL,   -- Need OR
    nonCriticalExtension                    SEQUENCE {}             OPTIONAL
}

RRCConnectionResumeComplete-NB ::= SEQUENCE {
    rrc-TransactionIdentifier               RRC-TransactionIdentifier,
    criticalExtensions                          CHOICE {
        rrcConnectionResumeComplete-r13             RRCConnectionResumeComplete-NB-r13-IEs,
        criticalExtensionsFuture                    SEQUENCE {}
    }
}

RRCConnectionResumeComplete-NB-r13-IEs ::= SEQUENCE {
    selectedPLMN-Identity-r13                   INTEGER (1..maxPLMN-r11)    OPTIONAL,
    dedicatedInfoNAS-r13                        DedicatedInfoNAS    OPTIONAL,
    lateNonCriticalExtension                    OCTET STRING                    OPTIONAL,
    nonCriticalExtension                        RRCConnectionResumeComplete-NB-v1470-IEs    OPTIONAL
}

RRCConnectionResumeComplete-NB-v1470-IEs ::= SEQUENCE {
    measResultServCell-r14                      MeasResultServCell-NB-r14   OPTIONAL,
    nonCriticalExtension                        RRCConnectionResumeComplete-NB-v1610-IEs    OPTIONAL
}

RRCConnectionResumeComplete-NB-v1610-IEs ::= SEQUENCE {
    rlf-InfoAvailable-r16               ENUMERATED {true}               OPTIONAL,
    anr-InfoAvailable-r16               ENUMERATED {true}               OPTIONAL,
    nonCriticalExtension                RRCConnectionResumeComplete-NB-v1710-IEs    OPTIONAL
}

RRCConnectionResumeComplete-NB-v1710-IEs ::= SEQUENCE {
    gnss-ValidityDuration-r17           GNSS-ValidityDuration-r17       OPTIONAL,   nonCriticalExtension                RRCConnectionResumeComplete-NB-v1800-IEs        OPTIONAL
}

RRCConnectionResumeComplete-NB-v1800-IEs ::= SEQUENCE {
    gnss-PositionFixDuration-r18        GNSS-PositionFixDuration-r18    OPTIONAL,
    nonCriticalExtension                SEQUENCE {}                     OPTIONAL
}

RRCConnectionResumeRequest-NB ::=   SEQUENCE {
    criticalExtensions                      CHOICE {
        rrcConnectionResumeRequest-r13          RRCConnectionResumeRequest-NB-r13-IEs,
        later                                   CHOICE {
            rrcConnectionResumeRequest-r16          RRCConnectionResumeRequest-5GC-NB-r16-IEs,
            criticalExtensionsFuture                SEQUENCE {}
        }
    }
}

RRCConnectionResumeRequest-NB-r13-IEs ::=   SEQUENCE {
    resumeID-r13                                ResumeIdentity-r13,
    shortResumeMAC-I-r13                        ShortMAC-I,
    resumeCause-r13                             EstablishmentCause-NB-r13,
    earlyContentionResolution-r14               BOOLEAN,
    cqi-NPDCCH-r14                              CQI-NPDCCH-NB-r14,
    anr-InfoAvailable-r16                       BOOLEAN,
    spare                                       BIT STRING (SIZE (3))
}

RRCConnectionResumeRequest-5GC-NB-r16-IEs ::=   SEQUENCE {
    resumeID-r16                                I-RNTI-r15,
    shortResumeMAC-I-r16                        ShortMAC-I,
    resumeCause-r16                             EstablishmentCause-NB-r13,
    cqi-NPDCCH-r16                              CQI-NPDCCH-NB-r14,
    spare                                       BIT STRING (SIZE (4))
}

RRCConnectionSetup-NB ::=       SEQUENCE {
    rrc-TransactionIdentifier           RRC-TransactionIdentifier,
    criticalExtensions                  CHOICE {
        c1                                  CHOICE {
            rrcConnectionSetup-r13              RRCConnectionSetup-NB-r13-IEs,
            spare1 NULL
        },
        criticalExtensionsFuture            SEQUENCE {}
    }
}

RRCConnectionSetup-NB-r13-IEs ::=       SEQUENCE {
    radioResourceConfigDedicated-r13        RadioResourceConfigDedicated-NB-r13,
    lateNonCriticalExtension                OCTET STRING                        OPTIONAL,
    nonCriticalExtension                    RRCConnectionSetup-NB-v1610-IEs OPTIONAL
}

RRCConnectionSetup-NB-v1610-IEs ::=     SEQUENCE {
    dedicatedInfoNAS-r16                    DedicatedInfoNAS            OPTIONAL,   -- Need ON
    nonCriticalExtension                    SEQUENCE {}                 OPTIONAL
}

RRCConnectionSetupComplete-NB ::=   SEQUENCE {
    rrc-TransactionIdentifier               RRC-TransactionIdentifier,
    criticalExtensions                      CHOICE{
            rrcConnectionSetupComplete-r13      RRCConnectionSetupComplete-NB-r13-IEs,
            criticalExtensionsFuture            SEQUENCE {}
    }
}

RRCConnectionSetupComplete-NB-r13-IEs ::= SEQUENCE {
    selectedPLMN-Identity-r13               INTEGER (1..maxPLMN-r11),
    s-TMSI-r13                              S-TMSI                          OPTIONAL,
    registeredMME-r13                       RegisteredMME                   OPTIONAL,
    dedicatedInfoNAS-r13                    DedicatedInfoNAS,
    attachWithoutPDN-Connectivity-r13       ENUMERATED {true}               OPTIONAL,
    up-CIoT-EPS-Optimisation-r13            ENUMERATED {true}               OPTIONAL,
    lateNonCriticalExtension                OCTET STRING                    OPTIONAL,
    nonCriticalExtension                    RRCConnectionSetupComplete-NB-v1430-IEs OPTIONAL
}

RRCConnectionSetupComplete-NB-v1430-IEs ::= SEQUENCE {
    gummei-Type-r14                         ENUMERATED { mapped}    OPTIONAL,
    dcn-ID-r14                              INTEGER (0..65535)          OPTIONAL,
    nonCriticalExtension                    RRCConnectionSetupComplete-NB-v1470-IEs OPTIONAL
}

RRCConnectionSetupComplete-NB-v1470-IEs ::= SEQUENCE {
    measResultServCell-r14                      MeasResultServCell-NB-r14   OPTIONAL,
    nonCriticalExtension                        RRCConnectionSetupComplete-NB-v1610-IEs OPTIONAL
}

RRCConnectionSetupComplete-NB-v1610-IEs ::= SEQUENCE {
    ng-5G-S-TMSI-r16                            NG-5G-S-TMSI-r15            OPTIONAL,
    registeredAMF-r16                           RegisteredAMF-r15           OPTIONAL,
    gummei-Type-v1610                           ENUMERATED {mappedFrom5G}   OPTIONAL,
    guami-Type-r16                              ENUMERATED {native, mapped} OPTIONAL,
    s-NSSAI-list-r16                            SEQUENCE(SIZE (1..maxNrofS-NSSAI-r15)) OF
                                                        S-NSSAI-r15     OPTIONAL,
    ng-U-DataTransfer-r16                       ENUMERATED {true}           OPTIONAL,
    up-CIoT-5GS-Optimisation-r16                ENUMERATED {true}           OPTIONAL,
    rlf-InfoAvailable-r16                       ENUMERATED {true}           OPTIONAL,
    anr-InfoAvailable-r16                       ENUMERATED {true}           OPTIONAL,
    pur-ConfigID-r16                            PUR-ConfigID-NB-r16     OPTIONAL,
    nonCriticalExtension                        RRCConnectionSetupComplete-NB-v1710-IEs OPTIONAL
}

RRCConnectionSetupComplete-NB-v1710-IEs ::= SEQUENCE {
    gnss-ValidityDuration-r17                   GNSS-ValidityDuration-r17   OPTIONAL,   nonCriticalExtension                        RRCConnectionSetupComplete-NB-v1800-IEs     OPTIONAL
}

RRCConnectionSetupComplete-NB-v1800-IEs ::= SEQUENCE {
    gnss-PositionFixDuration-r18                GNSS-PositionFixDuration-r18        OPTIONAL,
    nonCriticalExtension                        SEQUENCE {}                         OPTIONAL
}

RRCEarlyDataComplete-NB-r15 ::=     SEQUENCE {
    criticalExtensions                  CHOICE {
        rrcEarlyDataComplete-r15            RRCEarlyDataComplete-NB-r15-IEs,
        criticalExtensionsFuture            SEQUENCE {}
    }
}

RRCEarlyDataComplete-NB-r15-IEs ::= SEQUENCE {
    dedicatedInfoNAS-r15                DedicatedInfoNAS                OPTIONAL,   -- Need ON
    extendedWaitTime-r15                INTEGER (1..1800)               OPTIONAL,   -- Need ON
    redirectedCarrierInfo-r15           RedirectedCarrierInfo-NB-r13    OPTIONAL,   -- Need ON
    redirectedCarrierInfoExt-r15        RedirectedCarrierInfo-NB-v1430  OPTIONAL,   -- Cond Redirection
    nonCriticalExtension                RRCEarlyDataComplete-NB-v1590-IEs   OPTIONAL
}

RRCEarlyDataComplete-NB-v1590-IEs ::=   SEQUENCE {
    lateNonCriticalExtension                    OCTET STRING                    OPTIONAL,
    nonCriticalExtension                        RRCEarlyDataComplete-NB-v1700-IEs   OPTIONAL
}

RRCEarlyDataComplete-NB-v1700-IEs ::=   SEQUENCE {
    cbp-Index-r17               INTEGER (1..2)              OPTIONAL,   -- Need OR
    nonCriticalExtension        SEQUENCE {}             OPTIONAL
}

RRCEarlyDataRequest-NB-r15 ::=      SEQUENCE {
    criticalExtensions                  CHOICE {
        rrcEarlyDataRequest-r15             RRCEarlyDataRequest-NB-r15-IEs,
        later                               CHOICE {
            rrcEarlyDataRequest-r16             RRCEarlyDataRequest-5GC-NB-r16-IEs,
            criticalExtensionsFuture            SEQUENCE {}
        }
    }
}

RRCEarlyDataRequest-NB-r15-IEs ::=  SEQUENCE {
    s-TMSI-r15                          S-TMSI,
    establishmentCause-r15              ENUMERATED {mo-Data, mo-ExceptionData, delayTolerantAccess, mt-Access-v1610},
    cqi-NPDCCH-r15                      CQI-NPDCCH-NB-r14                       OPTIONAL,
    dedicatedInfoNAS-r15                DedicatedInfoNAS,
    nonCriticalExtension                RRCEarlyDataRequest-NB-v1590-IEs        OPTIONAL
}

RRCEarlyDataRequest-NB-v1590-IEs ::=    SEQUENCE {
    lateNonCriticalExtension                OCTET STRING                OPTIONAL,
    nonCriticalExtension                    SEQUENCE {}                 OPTIONAL
}

RRCEarlyDataRequest-5GC-NB-r16-IEs ::=  SEQUENCE {
    ng-5G-S-TMSI-r16                    NG-5G-S-TMSI-r15,
    establishmentCause-r16              ENUMERATED {mo-Data, mo-ExceptionData, mt-Access, spare1},
    cqi-NPDCCH-r16                      CQI-NPDCCH-NB-r14           OPTIONAL,
    dedicatedInfoNAS-r16                DedicatedInfoNAS,
    lateNonCriticalExtension            OCTET STRING                OPTIONAL,
    nonCriticalExtension                SEQUENCE {}                 OPTIONAL
}

SCPTMConfiguration-NB-r14 ::=   SEQUENCE {
    sc-mtch-InfoList-r14            SC-MTCH-InfoList-NB-r14,
    scptm-NeighbourCellList-r14     SCPTM-NeighbourCellList-NB-r14      OPTIONAL,   -- Need OP
    lateNonCriticalExtension        OCTET STRING                        OPTIONAL,
    nonCriticalExtension            SCPTMConfiguration-NB-v1610 OPTIONAL
}

SCPTMConfiguration-NB-v1610 ::= SEQUENCE {
    sc-mtch-InfoListMultiTB-r16     SC-MTCH-InfoList-NB-r14,
    multiTB-Gap-r16                 ENUMERATED {sf16, sf32, sf64, sf128}    OPTIONAL,   -- Need OR
    nonCriticalExtension            SEQUENCE {}                         OPTIONAL
}

SystemInformation-NB ::=        SEQUENCE {
    criticalExtensions                  CHOICE {
        systemInformation-r13               SystemInformation-NB-r13-IEs,
        criticalExtensionsFuture            SEQUENCE {}
    }
}
SystemInformation-NB-r13-IEs ::=    SEQUENCE {
    sib-TypeAndInfo-r13                 SEQUENCE (SIZE (1..maxSIB)) OF CHOICE {
        sib2-r13                            SystemInformationBlockType2-NB-r13,
        sib3-r13                            SystemInformationBlockType3-NB-r13,
        sib4-r13                            SystemInformationBlockType4-NB-r13,
        sib5-r13                            SystemInformationBlockType5-NB-r13,
        sib14-r13                           SystemInformationBlockType14-NB-r13,
        sib16-r13                           SystemInformationBlockType16-NB-r13,
        ...,
        sib15-v1430                         SystemInformationBlockType15-NB-r14,
        sib20-v1430                         SystemInformationBlockType20-NB-r14,
        sib22-v1430                         SystemInformationBlockType22-NB-r14,
        sib23-v1530                         SystemInformationBlockType23-NB-r15,
        sib27-v1610                         SystemInformationBlockType27-NB-r16,
        sib31-v1700                         SystemInformationBlockType31-NB-r17,
        sib32-v1700                         SystemInformationBlockType32-NB-r17,
        sib33-v1800                         SystemInformationBlockType33-NB-r18
    },
    lateNonCriticalExtension            OCTET STRING                        OPTIONAL,
    nonCriticalExtension                SEQUENCE {}                         OPTIONAL
}

SystemInformationBlockType1-NB ::=  SEQUENCE {
    hyperSFN-MSB-r13                    BIT STRING (SIZE (8)),
    cellAccessRelatedInfo-r13           SEQUENCE {
        plmn-IdentityList-r13               PLMN-IdentityList-NB-r13,
        trackingAreaCode-r13                TrackingAreaCode,
        cellIdentity-r13                    CellIdentity,
        cellBarred-r13                      ENUMERATED {barred, notBarred},
        intraFreqReselection-r13            ENUMERATED {allowed, notAllowed}
    },
    cellSelectionInfo-r13               SEQUENCE {
        q-RxLevMin-r13                      Q-RxLevMin,
        q-QualMin-r13                       Q-QualMin-r9
    },
    p-Max-r13                           P-Max                   OPTIONAL,   -- Need OP
    freqBandIndicator-r13               FreqBandIndicator-NB-r13,
    freqBandInfo-r13                    NS-PmaxList-NB-r13              OPTIONAL,   -- Need OR
    multiBandInfoList-r13               MultiBandInfoList-NB-r13        OPTIONAL,   -- Need OR
    downlinkBitmap-r13                  DL-Bitmap-NB-r13                OPTIONAL,   -- Cond SIB1
    eutraControlRegionSize-r13          ENUMERATED {n1, n2, n3}         OPTIONAL,   -- Cond inband
    nrs-CRS-PowerOffset-r13             ENUMERATED {dB-6,      dB-4dot77, dB-3,
                                                    dB-1dot77, dB0,       dB1,
                                                    dB1dot23,  dB2,       dB3,
                                                    dB4,       dB4dot23,  dB5,
                                                    dB6,       dB7,       dB8,
                                                    dB9}        OPTIONAL,   -- Cond inband-SamePCI
    schedulingInfoList-r13              SchedulingInfoList-NB-r13,
    si-WindowLength-r13                 ENUMERATED {ms160, ms320, ms480, ms640,
                                                    ms960, ms1280, ms1600, spare1},
    si-RadioFrameOffset-r13             INTEGER (1..15)     OPTIONAL,   -- Need OP
    systemInfoValueTagList-r13          SystemInfoValueTagList-NB-r13   OPTIONAL,   -- Need OR
    lateNonCriticalExtension            OCTET STRING                    OPTIONAL,
    nonCriticalExtension                SystemInformationBlockType1-NB-v1350    OPTIONAL
}

SystemInformationBlockType1-NB-v1350 ::=    SEQUENCE {
    cellSelectionInfo-v1350             CellSelectionInfo-NB-v1350  OPTIONAL,   -- Cond Qrxlevmin
    nonCriticalExtension                SystemInformationBlockType1-NB-v1430    OPTIONAL
}

SystemInformationBlockType1-NB-v1430 ::=    SEQUENCE {
    cellSelectionInfo-v1430             CellSelectionInfo-NB-v1430      OPTIONAL,   -- Need OR
    nonCriticalExtension                SystemInformationBlockType1-NB-v1450                    OPTIONAL
}

SystemInformationBlockType1-NB-v1450 ::= SEQUENCE {
    nrs-CRS-PowerOffset-v1450               ENUMERATED {dB-6,  dB-4dot77, dB-3,
                                                    dB-1dot77, dB0,       dB1,
                                                    dB1dot23,  dB2,       dB3,
                                                    dB4,       dB4dot23,  dB5,
                                                    dB6,       dB7,       dB8,
                                                    dB9}        OPTIONAL,   -- Cond inband-SamePCI-ExceptAnchor
    nonCriticalExtension                SystemInformationBlockType1-NB-v1530                    OPTIONAL
}

SystemInformationBlockType1-NB-v1530 ::= SEQUENCE {
    tdd-Parameters-r15                      SEQUENCE {
        tdd-Config-r15                          TDD-Config-NB-r15,
        tdd-SI-CarrierInfo-r15                  ENUMERATED {anchor, non-anchor},
        tdd-SI-SubframesBitmap-r15              DL-Bitmap-NB-r13        OPTIONAL    -- Cond TDD-SI-NonAnchor
    }   OPTIONAL,   -- Cond TDD
    schedulingInfoList-v1530            SchedulingInfoList-NB-v1530     OPTIONAL,   -- Need OR
    nonCriticalExtension                SystemInformationBlockType1-NB-v1610    OPTIONAL
}

SystemInformationBlockType1-NB-v1610 ::= SEQUENCE {
    cellAccessRelatedInfo-5GC-r16           SEQUENCE {
        plmn-IdentityList-r16               PLMN-IdentityList-5GC-NB-r16,
        trackingAreaCode-5GC-r16            TrackingAreaCode-5GC-r15,
        cellIdentity-r16                    CellIdentity    OPTIONAL,   -- Need OP
        cellBarred-5GC-r16                  ENUMERATED {barred, notBarred}
    }   OPTIONAL,   -- Need OR
    nonCriticalExtension                SystemInformationBlockType1-NB-v1700    OPTIONAL
}

SystemInformationBlockType1-NB-v1700 ::= SEQUENCE {
    cellAccessRelatedInfo-NTN-r17           SEQUENCE {
        cellBarred-NTN-r17                      ENUMERATED {barred, notBarred},
        plmn-IdentityList-v1700             PLMN-IdentityList-NB-v1700  OPTIONAL -- Need OR
    } OPTIONAL, -- Need OR
    nonCriticalExtension                        SEQUENCE {}                 OPTIONAL
}

PLMN-IdentityList-NB-r13 ::=        SEQUENCE (SIZE (1..maxPLMN-r11)) OF PLMN-IdentityInfo-NB-r13

PLMN-IdentityList-5GC-NB-r16 ::=    SEQUENCE (SIZE (1..maxPLMN-r11)) OF PLMN-IdentityInfo-5GC-NB-r16

PLMN-IdentityList-NB-v1700::=       SEQUENCE (SIZE (1..maxPLMN-r11)) OF PLMN-IdentityInfo-NB-v1700

PLMN-IdentityInfo-NB-r13 ::=        SEQUENCE {
    plmn-Identity-r13                       PLMN-Identity,
    cellReservedForOperatorUse-r13          ENUMERATED {reserved, notReserved},
    attachWithoutPDN-Connectivity-r13       ENUMERATED {true}   OPTIONAL    -- Need OP
}

PLMN-IdentityInfo-5GC-NB-r16 ::=    SEQUENCE {
    plmn-Identity-5GC-r16                   CHOICE {
        plmn-Identity-r16                       PLMN-Identity,
        plmn-Index-r16                          INTEGER (1..maxPLMN-r11)
        },
    cellReservedForOperatorUse-r16          ENUMERATED {reserved, notReserved},
    ng-U-DataTransfer-r16                   ENUMERATED {true}   OPTIONAL,   -- Need OR
    up-CIoT-5GS-Optimisation-r16            ENUMERATED {true}   OPTIONAL    -- Need OR
}

PLMN-IdentityInfo-NB-v1700 ::=  SEQUENCE {
    trackingAreaList-r17            TrackingAreaList-NB-r17         OPTIONAL    -- Need OP
}

TrackingAreaList-NB-r17 ::= SEQUENCE (SIZE (1..maxTAC-NB-r17)) OF  TrackingAreaCode

SchedulingInfoList-NB-r13 ::= SEQUENCE (SIZE (1..maxSI-Message-NB-r13)) OF SchedulingInfo-NB-r13

SchedulingInfoList-NB-v1530 ::= SEQUENCE (SIZE (1..maxSI-Message-NB-r13)) OF SchedulingInfo-NB-v1530

SchedulingInfo-NB-r13::=        SEQUENCE {
    si-Periodicity-r13              ENUMERATED {rf64, rf128, rf256, rf512,
                                                rf1024, rf2048, rf4096, spare},
    si-RepetitionPattern-r13        ENUMERATED {every2ndRF, every4thRF, every8thRF, every16thRF},
    sib-MappingInfo-r13             SIB-MappingInfo-NB-r13,
    si-TB-r13                       ENUMERATED {b56, b120, b208, b256, b328, b440, b552, b680}
}

SchedulingInfo-NB-v1530::=      SEQUENCE {
    sib-MappingInfo-v1530               SIB-MappingInfo-NB-v1530    OPTIONAL    -- Need OR
}

SystemInfoValueTagList-NB-r13 ::=   SEQUENCE (SIZE (1.. maxSI-Message-NB-r13)) OF
                                        SystemInfoValueTagSI-r13

SIB-MappingInfo-NB-r13 ::=          SEQUENCE (SIZE (0..maxSIB-1)) OF SIB-Type-NB-r13

SIB-MappingInfo-NB-v1530 ::=        SEQUENCE (SIZE (1..8)) OF SIB-Type-NB-v1530

SIB-Type-NB-r13 ::=                 ENUMERATED {
                                        sibType3-NB-r13, sibType4-NB-r13, sibType5-NB-r13,
                                        sibType14-NB-r13, sibType16-NB-r13, sibType15-NB-r14,
                                        sibType20-NB-r14, sibType22-NB-r14}

SIB-Type-NB-v1530 ::=               ENUMERATED {
                                        sibType23-NB-r15, sibType27-NB-r16, sibType31-NB-r17,
                                        sibType32-NB-r17, sibType33-NB-r18, spare3, spare2,
                                        spare1
}

CellSelectionInfo-NB-v1350 ::=      SEQUENCE {
    delta-RxLevMin-v1350                INTEGER (-8..-1)
}

CellSelectionInfo-NB-v1430 ::=      SEQUENCE {
    powerClass14dBm-Offset-r14          ENUMERATED {dB-6, dB-3, dB3, dB6, dB9, dB12}    OPTIONAL,   --  Need OP
    ce-authorisationOffset-r14          ENUMERATED {dB5, dB10, dB15, dB20, dB25, dB30, dB35}    OPTIONAL    --  Need OP
}

UECapabilityEnquiry-NB ::=  SEQUENCE {
    rrc-TransactionIdentifier           RRC-TransactionIdentifier,
    criticalExtensions                  CHOICE {
        c1                                  CHOICE {
            ueCapabilityEnquiry-r13             UECapabilityEnquiry-NB-r13-IEs,
            spare1                              NULL
        },
        criticalExtensionsFuture            SEQUENCE {}
    }
}

UECapabilityEnquiry-NB-r13-IEs ::=  SEQUENCE {
    lateNonCriticalExtension            OCTET STRING                        OPTIONAL,
    nonCriticalExtension                SEQUENCE {}                         OPTIONAL
}

UECapabilityInformation-NB ::=  SEQUENCE {
    rrc-TransactionIdentifier           RRC-TransactionIdentifier,
    criticalExtensions                  CHOICE{
            ueCapabilityInformation-r13     UECapabilityInformation-NB-r13-IEs,
            criticalExtensionsFuture        SEQUENCE {}
    }
}

UECapabilityInformation-NB-r13-IEs ::=  SEQUENCE {
    ue-Capability-r13                       UE-Capability-NB-r13,
    ue-RadioPagingInfo-r13                  UE-RadioPagingInfo-NB-r13,
    lateNonCriticalExtension                OCTET STRING                        OPTIONAL,
    nonCriticalExtension                    UECapabilityInformation-NB-Ext-r14-IEs                          OPTIONAL
}

UECapabilityInformation-NB-Ext-r14-IEs ::=  SEQUENCE {
    ue-Capability-ContainerExt-r14          OCTET STRING (CONTAINING UE-Capability-NB-Ext-r14-IEs),
    nonCriticalExtension                    SEQUENCE {}                         OPTIONAL
}

UEInformationRequest-NB-r16 ::=         SEQUENCE {
    rrc-TransactionIdentifier           RRC-TransactionIdentifier,
    criticalExtensions                  CHOICE {
        ueInformationRequest-r16            UEInformationRequest-NB-r16-IEs,
        criticalExtensionsFuture            SEQUENCE {}
    }
}

UEInformationRequest-NB-r16-IEs ::=     SEQUENCE {
    rach-ReportReq-r16                  BOOLEAN,
    rlf-ReportReq-r16                   BOOLEAN,
    anr-ReportReq-r16                   BOOLEAN,
    lateNonCriticalExtension            OCTET STRING                        OPTIONAL,
    nonCriticalExtension                SEQUENCE {}                         OPTIONAL
}

UEInformationResponse-NB-r16        ::=     SEQUENCE {
    rrc-TransactionIdentifier           RRC-TransactionIdentifier,
    criticalExtensions                  CHOICE {
        ueInformationResponse-r16           UEInformationResponse-NB-r16-IEs,
        criticalExtensionsFuture            SEQUENCE {}
    }
}

UEInformationResponse-NB-r16-IEs ::=    SEQUENCE {
    rach-Report-r16                         RACH-Report-NB-r16                  OPTIONAL,
    rlf-Report-r16                          RLF-Report-NB-r16                   OPTIONAL,
    anr-MeasReport-r16                      ANR-MeasReport-NB-r16               OPTIONAL,
    lateNonCriticalExtension                OCTET STRING                        OPTIONAL,
    nonCriticalExtension                    SEQUENCE {}                         OPTIONAL
}

RACH-Report-NB-r16 ::=                  SEQUENCE {
    numberOfPreamblesSent-r16               INTEGER (1..64),
    contentionDetected-r16                  BOOLEAN,
    initialNRSRP-Level-r16                  INTEGER (0..2),
    edt-Fallback-r16                        BOOLEAN
}

RLF-Report-NB-r16 ::=                   SEQUENCE {
    failedPCellId-r16                       CellGlobalIdEUTRA,
    reestablishmentCellId-r16               CellGlobalIdEUTRA                   OPTIONAL,
    locationInfo-r16                        LocationInfo-r10                    OPTIONAL,
    measResultLastServCell-r16              SEQUENCE {
        nrsrpResult-r16                         NRSRP-Range-NB-r14,
        nrsrqResult-r16                         NRSRQ-Range-NB-r14              OPTIONAL
    },
    timeSinceFailure-r16                    TimeSinceFailure-r11                OPTIONAL
}

ULInformationTransfer-NB ::=    SEQUENCE {
    criticalExtensions                  CHOICE {
            ulInformationTransfer-r13       ULInformationTransfer-NB-r13-IEs,
            criticalExtensionsFuture        SEQUENCE {}
    }
}

ULInformationTransfer-NB-r13-IEs ::=    SEQUENCE {
    dedicatedInfoNAS-r13                    DedicatedInfoNAS,
    lateNonCriticalExtension                OCTET STRING                    OPTIONAL,
    nonCriticalExtension                    SEQUENCE {}                     OPTIONAL
}

SystemInformationBlockType2-NB-r13 ::=  SEQUENCE {
    radioResourceConfigCommon-r13           RadioResourceConfigCommonSIB-NB-r13,
    ue-TimersAndConstants-r13               UE-TimersAndConstants-NB-r13,
    freqInfo-r13                            SEQUENCE {
        ul-CarrierFreq-r13                      CarrierFreq-NB-r13          OPTIONAL,   -- Need OP
        additionalSpectrumEmission-r13          AdditionalSpectrumEmission
    },
    timeAlignmentTimerCommon-r13            TimeAlignmentTimer,
    multiBandInfoList-r13   SEQUENCE (SIZE (1..maxMultiBands)) OF AdditionalSpectrumEmission        OPTIONAL,   -- Need OR
    lateNonCriticalExtension                OCTET STRING                    OPTIONAL,
    ...,
    [[  cp-Reestablishment-r14              ENUMERATED {true}               OPTIONAL        -- Need OP
    ]],
    [[  servingCellMeasInfo-r14             ENUMERATED {true}               OPTIONAL,       -- Need OR
        cqi-Reporting-r14                   ENUMERATED {true}               OPTIONAL        -- Need OR
    ]],
    [[  enhancedPHR-r15                     ENUMERATED {true}       OPTIONAL,   -- Need OR
        freqInfo-v1530                      SEQUENCE {
            tdd-UL-DL-AlignmentOffset-r15       TDD-UL-DL-AlignmentOffset-NB-r15
        }   OPTIONAL,       -- Cond TDD
        cp-EDT-r15                          ENUMERATED {true}       OPTIONAL,   -- Need OR
        up-EDT-r15                          ENUMERATED {true}       OPTIONAL    -- Need OR
    ]],
    [[  earlySecurityReactivation-r16       ENUMERATED {true}       OPTIONAL,   -- Need OR
        cp-EDT-5GC-r16                      ENUMERATED {true}       OPTIONAL,   -- Need OR
        up-EDT-5GC-r16                      ENUMERATED {true}       OPTIONAL,   -- Need OR
        cp-PUR-EPC-r16                      ENUMERATED {true}       OPTIONAL,   -- Need OR
        up-PUR-EPC-r16                      ENUMERATED {true}       OPTIONAL,   -- Need OR
        cp-PUR-5GC-r16                      ENUMERATED {true}       OPTIONAL,   -- Need OR
        up-PUR-5GC-r16                      ENUMERATED {true}       OPTIONAL,   -- Need OR
        rai-ActivationEnh-r16               ENUMERATED {true}       OPTIONAL    -- Need OR
    ]],
    [[  gnss-PositionFixDurationReporting-r18   ENUMERATED {true}       OPTIONAL    -- Need OR
    ]]
}

SystemInformationBlockType3-NB-r13 ::=  SEQUENCE {
    cellReselectionInfoCommon-r13           SEQUENCE {
        q-Hyst-r13                              ENUMERATED {
                                                    dB0, dB1, dB2, dB3, dB4, dB5, dB6, dB8, dB10,
                                                    dB12, dB14, dB16, dB18, dB20, dB22, dB24
                                                    }
    },
    cellReselectionServingFreqInfo-r13      SEQUENCE {
        s-NonIntraSearch-r13                    ReselectionThreshold
    },
    intraFreqCellReselectionInfo-r13        SEQUENCE {
        q-RxLevMin-r13                          Q-RxLevMin,
        q-QualMin-r13                           Q-QualMin-r9            OPTIONAL,   -- Need OP
        p-Max-r13                               P-Max                   OPTIONAL,   -- Need OP
        s-IntraSearchP-r13                      ReselectionThreshold,
        t-Reselection-r13                       T-Reselection-NB-r13
    },
    freqBandInfo-r13                        NS-PmaxList-NB-r13              OPTIONAL,   -- Need OR
    multiBandInfoList-r13                   SEQUENCE (SIZE (1..maxMultiBands)) OF
                                                NS-PmaxList-NB-r13          OPTIONAL,   -- Need OR
    lateNonCriticalExtension                    OCTET STRING                OPTIONAL,
    ...,
    [[  intraFreqCellReselectionInfo-v1350  IntraFreqCellReselectionInfo-NB-v1350 OPTIONAL  -- Cond Qrxlevmin
    ]],
    [[  intraFreqCellReselectionInfo-v1360  IntraFreqCellReselectionInfo-NB-v1360 OPTIONAL  -- Need OR
    ]],
    [[  intraFreqCellReselectionInfo-v1430  IntraFreqCellReselectionInfo-NB-v1430 OPTIONAL  -- Need OR
    ]],
    [[  cellReselectionInfoCommon-v1450     CellReselectionInfoCommon-NB-v1450  OPTIONAL    -- Need OR
    ]],
    [[  nsss-RRM-Config-r15                 NSSS-RRM-Config-NB-r15  OPTIONAL,   -- Need OR
        npbch-RRM-Config-r15                ENUMERATED {enabled}    OPTIONAL    -- Need OR
    ]],
    [[  connMeasConfig-r17                  ConnMeasConfig-NB-r17   OPTIONAL,   -- Need OR
        t-Service-r17                       TimeOffsetUTC-r17               OPTIONAL    -- Need OR
    ]],
    [[  satelliteAssistanceInfo-r18     SEQUENCE (SIZE(1..maxSat-r17))  OF SatelliteId-r18  OPTIONAL    -- Need OR
    ]]
}

IntraFreqCellReselectionInfo-NB-v1350 ::=   SEQUENCE {
    delta-RxLevMin-v1350                        INTEGER (-8..-1)
}

IntraFreqCellReselectionInfo-NB-v1360 ::=   SEQUENCE {
    s-IntraSearchP-v1360                            ReselectionThreshold-NB-v1360
}

IntraFreqCellReselectionInfo-NB-v1430 ::=   SEQUENCE {
    powerClass14dBm-Offset-r14      ENUMERATED {dB-6, dB-3, dB3, dB6, dB9, dB12}    OPTIONAL,   -- Need OP
    ce-AuthorisationOffset-r14      ENUMERATED {dB5, dB10, dB15, dB20, dB25, dB30, dB35}    OPTIONAL    -- Need OP
}

CellReselectionInfoCommon-NB-v1450 ::=  SEQUENCE {
    s-SearchDeltaP-r14                  ENUMERATED {dB6, dB9, dB12, dB15}
}

ConnMeasConfig-NB-r17 ::= SEQUENCE {
    s-MeasureIntra-r17      NRSRP-Range-NB-r14,
    s-MeasureInter-r17      NRSRP-Range-NB-r14  OPTIONAL,   -- Need OP
    neighCellMeasCriteria-r17       SEQUENCE {
                s-MeasureDeltaP-r17     ENUMERATED {dB6, dB9, dB12, dB15},
                t-MeasureDeltaP-r17     ENUMERATED {s15, s30, s45, s60}
            }   OPTIONAL    -- Need OR
}

SystemInformationBlockType4-NB-r13 ::=      SEQUENCE {
    intraFreqNeighCellList-r13          IntraFreqNeighCellList  OPTIONAL,   -- Need OR
    intraFreqExcludedCellList-r13           IntraFreqExcludedCellList   OPTIONAL,   -- Need OR
    lateNonCriticalExtension            OCTET STRING            OPTIONAL,
    ...,
    [[  nsss-RRM-Config-r15             NSSS-RRM-Config-NB-r15  OPTIONAL,   -- Need OR
        intraFreqNeighCellList-v1530    IntraFreqNeighCellList-NB-v1530 OPTIONAL    -- Need OR
    ]]
}

IntraFreqNeighCellList-NB-v1530 ::=     SEQUENCE (SIZE (1..maxCellIntra)) OF IntraFreqNeighCellInfo-NB-v1530

IntraFreqNeighCellInfo-NB-v1530 ::=     SEQUENCE {
    nsss-RRM-Config-r15                     NSSS-RRM-Config-NB-r15  OPTIONAL    -- Cond NSSS-RRM
}

SystemInformationBlockType5-NB-r13 ::=  SEQUENCE {
    interFreqCarrierFreqList-r13            InterFreqCarrierFreqList-NB-r13,
    t-Reselection-r13                       T-Reselection-NB-r13,
    lateNonCriticalExtension                OCTET STRING                    OPTIONAL,
    ...,
    [[  scptm-FreqOffset-r14                INTEGER (1..8)                  OPTIONAL    -- Need OP
    ]]
}


InterFreqCarrierFreqList-NB-r13 ::=     SEQUENCE (SIZE (1..maxFreq)) OF InterFreqCarrierFreqInfo-NB-r13


InterFreqCarrierFreqInfo-NB-r13 ::= SEQUENCE {
    dl-CarrierFreq-r13                  CarrierFreq-NB-r13,
    q-RxLevMin-r13                      Q-RxLevMin,
    q-QualMin-r13                       Q-QualMin-r9                    OPTIONAL,       -- Need OP
    p-Max-r13                           P-Max                           OPTIONAL,       -- Need OP
    q-OffsetFreq-r13                    Q-OffsetRange                   DEFAULT dB0,
    interFreqNeighCellList-r13          InterFreqNeighCellList-NB-r13   OPTIONAL,       -- Need OR
    interFreqExcludedCellList-r13           InterFreqExcludedCellList-NB-r13    OPTIONAL,       -- Need OR
    multiBandInfoList-r13               MultiBandInfoList-NB-r13        OPTIONAL,       -- Need OR
    ...,
    [[  delta-RxLevMin-v1350            INTEGER (-8..-1)        OPTIONAL    -- Cond Qrxlevmin
    ]],
    [[  powerClass14dBm-Offset-r14      ENUMERATED {dB-6, dB-3, dB3, dB6, dB9, dB12}
OPTIONAL,   --  Need OP
        ce-AuthorisationOffset-r14      ENUMERATED {dB5, dB10, dB15, dB20, dB25, dB30, dB35}    OPTIONAL    -- Need OP
    ]],
    [[  nsss-RRM-Config-r15             NSSS-RRM-Config-NB-r15  OPTIONAL,   -- Need OR
        interFreqNeighCellList-v1530    InterFreqNeighCellList-NB-v1530 OPTIONAL -- Need OR
    ]],
    [[  dl-CarrierFreq-v1550            CarrierFreq-NB-v1550    OPTIONAL -- Cond TDD
    ]],
    [[  satelliteAssistanceInfo-r18 SEQUENCE (SIZE(1..maxSat-r17)) OF SatelliteId-r18   OPTIONAL    -- Need OR
    ]]
}

InterFreqNeighCellList-NB-r13 ::=       SEQUENCE (SIZE (1..maxCellInter)) OF PhysCellId

InterFreqNeighCellList-NB-v1530 ::=     SEQUENCE (SIZE (1..maxCellInter)) OF InterFreqNeighCellInfo-NB-v1530

InterFreqNeighCellInfo-NB-v1530 ::=     SEQUENCE {
    nsss-RRM-Config-r15                     NSSS-RRM-Config-NB-r15  OPTIONAL    -- Cond NSSS-RRM
}

InterFreqExcludedCellList-NB-r13 ::=        SEQUENCE (SIZE (1..maxExcludedCell)) OF PhysCellId

SystemInformationBlockType14-NB-r13 ::= SEQUENCE {
    ab-Param-r13                    CHOICE {
        ab-Common-r13                   AB-Config-NB-r13,
        ab-PerPLMN-List-r13             SEQUENCE (SIZE (1..maxPLMN-r11)) OF AB-ConfigPLMN-NB-r13
    }                                                           OPTIONAL, -- Need OR
    lateNonCriticalExtension        OCTET STRING                OPTIONAL,
    ...,
    [[  ab-PerNRSRP-r15             ENUMERATED {thresh1, thresh2}   OPTIONAL    --  Need OR
    ]],
    [[  uac-Param-r16               UAC-Param-NB-r16                OPTIONAL    --  Need OR
    ]]
}

AB-ConfigPLMN-NB-r13 ::=    SEQUENCE {
    ab-Config-r13                   AB-Config-NB-r13            OPTIONAL -- Need OR
}

AB-Config-NB-r13 ::=        SEQUENCE {
    ab-Category-r13                 ENUMERATED {a, b, c},
    ab-BarringBitmap-r13            BIT STRING (SIZE(10)),
    ab-BarringForExceptionData-r13  ENUMERATED {true}           OPTIONAL,   -- Need OP
    ab-BarringForSpecialAC-r13      BIT STRING (SIZE(5))
}

UAC-Param-NB-r16    ::=     CHOICE {
    uac-BarringCommon           UAC-Barring-NB-r16,
    uac-BarringPerPLMN-List     SEQUENCE (SIZE (1..maxPLMN-r11)) OF UAC-Barring-NB-r16
}

UAC-Barring-NB-r16  ::=     SEQUENCE {
    uac-BarringPerCatList-r16           UAC-BarringPerCatList-NB-r16    OPTIONAL,   -- Need OR
    uac-AC1-SelectAssistInfo-r16        UAC-AC1-SelectAssistInfo-r15    OPTIONAL,   -- Need OR
    uac-BarringForAccessIdentity-r16    BIT STRING (SIZE(7))
}

UAC-BarringPerCatList-NB-r16 ::= SEQUENCE (SIZE (1..maxAccessCat-1-r15)) OF UAC-BarringPerCat-NB-r16

UAC-BarringPerCat-NB-r16 ::=    SEQUENCE {
    uac-accessCategory-r16          INTEGER (1..maxAccessCat-1-r15),
    uac-BarringFactor-r16           ENUMERATED {p00, p05, p10, p15, p20, p25, p30, p40,
                                                p50, p60, p70, p75, p80, p85, p90, p95},
    uac-BarringTime-r16             ENUMERATED {s4, s8, s16, s32, s64, s128, s256, s512}
}

SystemInformationBlockType15-NB-r14 ::= SEQUENCE {
    mbms-SAI-IntraFreq-r14                  MBMS-SAI-List-r11               OPTIONAL,   -- Need OR
    mbms-SAI-InterFreqList-r14              MBMS-SAI-InterFreqList-NB-r14   OPTIONAL,   -- Need OR
    lateNonCriticalExtension                OCTET STRING                    OPTIONAL,
    ...
}

MBMS-SAI-InterFreqList-NB-r14 ::=       SEQUENCE (SIZE (1..maxFreq)) OF MBMS-SAI-InterFreq-NB-r14

MBMS-SAI-InterFreq-NB-r14 ::=           SEQUENCE {
    dl-CarrierFreq-r14                      CarrierFreq-NB-r13,
    mbms-SAI-List-r14                       MBMS-SAI-List-r11,
    multiBandInfoList-r14                   AdditionalBandInfoList-NB-r14   OPTIONAL    -- Need OR
}

SystemInformationBlockType16-NB-r13 ::= SystemInformationBlockType16-r11

SystemInformationBlockType20-NB-r14 ::= SEQUENCE {
    npdcch-SC-MCCH-Config-r14               NPDCCH-SC-MCCH-Config-NB-r14,
    sc-mcch-CarrierConfig-r14               CHOICE {
        dl-CarrierConfig-r14                    DL-CarrierConfigCommon-NB-r14,
        dl-CarrierIndex-r14                     INTEGER (0.. maxNonAnchorCarriers-NB-r14)
    },
    sc-mcch-RepetitionPeriod-r14            ENUMERATED {rf32, rf128, rf512, rf1024,
                                                        rf2048, rf4096, rf8192, rf16384},
    sc-mcch-Offset-r14                      INTEGER (0..10),
    sc-mcch-ModificationPeriod-r14          ENUMERATED { rf32, rf128, rf256, rf512, rf1024,
                                                    rf2048, rf4096, rf8192, rf16384, rf32768,
                                                    rf65536, rf131072, rf262144, rf524288,
                                                    rf1048576, spare1},
    sc-mcch-SchedulingInfo-r14              SC-MCCH-SchedulingInfo-NB-r14       OPTIONAL,   -- Need OP
    lateNonCriticalExtension                OCTET STRING                        OPTIONAL,
    ...
}

NPDCCH-SC-MCCH-Config-NB-r14 ::=    SEQUENCE {
    npdcch-NumRepetitions-SC-MCCH-r14       ENUMERATED {r1, r2, r4, r8, r16,
                                                        r32, r64, r128, r256,
                                                        r512, r1024, r2048},
    npdcch-StartSF-SC-MCCH-r14              ENUMERATED {v1dot5, v2, v4, v8,
                                                        v16, v32, v48, v64},
    npdcch-Offset-SC-MCCH-r14               ENUMERATED {zero, oneEighth, oneQuarter,
                                                        threeEighth, oneHalf, fiveEighth,
                                                        threeQuarter, sevenEighth}
}

SC-MCCH-SchedulingInfo-NB-r14::=    SEQUENCE    {
    onDurationTimerSCPTM-r14                    ENUMERATED {
                                                    pp1, pp2, pp3, pp4,
                                                    pp8, pp16, pp32, spare},
    drx-InactivityTimerSCPTM-r14                ENUMERATED {
                                                    pp0, pp1, pp2, pp3,
                                                    pp4, pp8, pp16, pp32},
    schedulingPeriodStartOffsetSCPTM-r14        CHOICE {
        sf10                                        INTEGER(0..9),
        sf20                                        INTEGER(0..19),
        sf32                                        INTEGER(0..31),
        sf40                                        INTEGER(0..39),
        sf64                                        INTEGER(0..63),
        sf80                                        INTEGER(0..79),
        sf128                                       INTEGER(0..127),
        sf160                                       INTEGER(0..159),
        sf256                                       INTEGER(0..255),
        sf320                                       INTEGER(0..319),
        sf512                                       INTEGER(0..511),
        sf640                                       INTEGER(0..639),
        sf1024                                      INTEGER(0..1023),
        sf2048                                      INTEGER(0..2047),
        sf4096                                      INTEGER(0..4095),
        sf8192                                      INTEGER(0..8191)
    },
    ...
}

SystemInformationBlockType22-NB-r14 ::= SEQUENCE {
    dl-ConfigList-r14                   DL-ConfigCommonList-NB-r14  OPTIONAL,   -- Need OR
    ul-ConfigList-r14                   UL-ConfigCommonList-NB-r14  OPTIONAL,   -- Need OR
    pagingWeightAnchor-r14              PagingWeight-NB-r14         OPTIONAL,   -- Cond pcch-config
    nprach-ProbabilityAnchorList-r14    NPRACH-ProbabilityAnchorList-NB-r14 OPTIONAL,   -- Cond nprach-config
    lateNonCriticalExtension            OCTET STRING                    OPTIONAL,
    ...,
    [[  mixedOperationModeConfig-r15    SEQUENCE {
            dl-ConfigListMixed-r15          DL-ConfigCommonList-NB-r14  OPTIONAL,   -- Cond dl-ConfigList
            ul-ConfigListMixed-r15          UL-ConfigCommonList-NB-r14  OPTIONAL,   -- Cond ul-ConfigList
            pagingDistribution-r15          ENUMERATED {true}           OPTIONAL,   -- Need OR
            nprach-Distribution-r15         ENUMERATED {true}           OPTIONAL    -- Need OR
        }                                                               OPTIONAL,   -- Need OR
        ul-ConfigList-r15               UL-ConfigCommonListTDD-NB-r15   OPTIONAL    -- Cond TDD
    ]],
    [[  coverageBasedPagingConfig-r17   CoverageBasedPagingConfig-NB-r17    OPTIONAL    -- Need OR
    ]]
}

DL-ConfigCommonList-NB-r14 ::=      SEQUENCE (SIZE (1.. maxNonAnchorCarriers-NB-r14)) OF
                                            DL-ConfigCommon-NB-r14

UL-ConfigCommonList-NB-r14 ::=      SEQUENCE (SIZE (1.. maxNonAnchorCarriers-NB-r14)) OF
                                            UL-ConfigCommon-NB-r14

UL-ConfigCommonListTDD-NB-r15 ::=   SEQUENCE (SIZE (1.. maxNonAnchorCarriers-NB-r14)) OF
                                            UL-ConfigCommonTDD-NB-r15

CoverageBasedPagingConfig-NB-r17 ::=    SEQUENCE {
    cbp-HystTimer-r17   ENUMERATED {ms2560, ms7680, ms12800, ms17920, ms23040, ms28160, ms33280, ms40960},
    cbp-ConfigList-r17  SEQUENCE (SIZE (1.. 2)) OF CBP-Config-NB-r17
}

CBP-Config-NB-r17 ::=   SEQUENCE {
    nrsrpMin-r17    RSRP-Range,
    nB-r17  ENUMERATED {fourT, twoT, oneT, halfT, quarterT, one8thT, one16thT, one32ndT,
                            one64thT, one128thT, one256thT, one512thT, one1024thT, spare3,
                        spare2, spare1} OPTIONAL,   -- Need OP
    ue-SpecificDRX-CycleMin-r17 ENUMERATED {rf32, rf64, rf128, rf256}   OPTIONAL    -- Need OR
}

DL-ConfigCommon-NB-r14 ::=          SEQUENCE {
    dl-CarrierConfig-r14                DL-CarrierConfigCommon-NB-r14,
    pcch-Config-r14                 PCCH-Config-NB-r14          OPTIONAL, -- Need OR
    ...,
    [[  wus-Config-r15                  WUS-ConfigPerCarrier-NB-r15     OPTIONAL    -- Cond WUS
    ]],
    [[  gwus-Config-r16                 WUS-ConfigPerCarrier-NB-r15     OPTIONAL    -- Cond GWUS
    ]],
    [[  pcch-Config-r17             PCCH-Config-NB-r17  OPTIONAL    -- Cond pcch-config2
    ]]
}

PCCH-Config-NB-r14 ::=              SEQUENCE {
    npdcch-NumRepetitionPaging-r14      ENUMERATED {
                                            r1, r2, r4, r8, r16, r32, r64, r128,
                                            r256, r512, r1024, r2048,
                                            spare4, spare3, spare2, spare1} OPTIONAL, -- Need OP
    pagingWeight-r14                        PagingWeight-NB-r14 DEFAULT w1,
    ...
}

PCCH-Config-NB-r17 ::= SEQUENCE {
    cbp-Index-r17                   INTEGER (1..2),
    npdcch-NumRepetitionPaging-r17  ENUMERATED {r1, r2, r4, r8, r16, r32, r64, r128},
    pagingWeight-r17                PagingWeight-NB-r14 DEFAULT w1,
    ...
}

PagingWeight-NB-r14 ::=         ENUMERATED {w1, w2, w3, w4, w5, w6, w7, w8,
                                                w9, w10, w11, w12, w13, w14, w15, w16}

UL-ConfigCommon-NB-r14 ::=          SEQUENCE {
    ul-CarrierFreq-r14                  CarrierFreq-NB-r13,
    nprach-ParametersList-r14           NPRACH-ParametersList-NB-r14    OPTIONAL, -- Need OR
    ...,
    [[  nprach-ParametersListEDT-r15    NPRACH-ParametersList-NB-r14    OPTIONAL -- Cond EDT
    ]],
    [[  rsrp-ThresholdsPrachInfoList-r16    RSRP-ThresholdsNPRACH-InfoList-NB-r13   OPTIONAL -- Need OR
    ]]
}

UL-ConfigCommonTDD-NB-r15 ::=       SEQUENCE {
    tdd-UL-DL-AlignmentOffset-r15       TDD-UL-DL-AlignmentOffset-NB-r15,
    nprach-ParametersListTDD-r15        NPRACH-ParametersListTDD-NB-r15 OPTIONAL, -- Need OR
    ...
}

NPRACH-ProbabilityAnchorList-NB-r14 ::= SEQUENCE (SIZE (1.. maxNPRACH-Resources-NB-r13)) OF
                                                NPRACH-ProbabilityAnchor-NB-r14

NPRACH-ProbabilityAnchor-NB-r14 ::=     SEQUENCE {
    nprach-ProbabilityAnchor-r14            ENUMERATED {
                                                zero, oneSixteenth, oneFifteenth, oneFourteenth,
                                                oneThirteenth, oneTwelfth, oneEleventh, oneTenth,
                                                oneNinth, oneEighth, oneSeventh, oneSixth,
                                                oneFifth, oneFourth, oneThird, oneHalf}
                                                        OPTIONAL    -- Need OP
}

SystemInformationBlockType23-NB-r15 ::= SEQUENCE {
    ul-ConfigList-v1530                 UL-ConfigCommonList-NB-v1530    OPTIONAL,   -- Need OR
    ul-ConfigListMixed-v1530                UL-ConfigCommonList-NB-v1530    OPTIONAL,   -- Need OR
    lateNonCriticalExtension                OCTET STRING                    OPTIONAL,
    ...
}

UL-ConfigCommonList-NB-v1530 ::=        SEQUENCE (SIZE (1.. maxNonAnchorCarriers-NB-r14)) OF
                                            UL-ConfigCommon-NB-v1530

UL-ConfigCommon-NB-v1530 ::=            SEQUENCE {
    nprach-ParametersListFmt2-r15           NPRACH-ParametersListFmt2-NB-r15    OPTIONAL, -- Need OR
    nprach-ParametersListFmt2EDT-r15        NPRACH-ParametersListFmt2-NB-r15    OPTIONAL, -- Cond EDT
    ...
}

SystemInformationBlockType27-NB-r16 ::= SEQUENCE {
    carrierFreqListEUTRA-r16                CarrierFreqListEUTRA-NB-r16     OPTIONAL,   -- Need OR
    carrierFreqsListGERAN-r16               CarrierFreqsListGERAN-NB-r16    OPTIONAL,   -- Need OR
    lateNonCriticalExtension                OCTET STRING                    OPTIONAL,
    ...
}

CarrierFreqListEUTRA-NB-r16 ::=         SEQUENCE (SIZE (1..maxFreqEUTRA-NB-r16)) OF
                                                    CarrierFreqEUTRA-NB-r16

CarrierFreqsListGERAN-NB-r16 ::=        SEQUENCE (SIZE (1..maxFreqsGERAN-NB-r16)) OF
                                                    CarrierFreqsGERAN-NB-r16


CarrierFreqEUTRA-NB-r16 ::=             SEQUENCE {
    carrierFreq-r16                         ARFCN-ValueEUTRA-r9,
    sib1-r16                                ENUMERATED {supported}      OPTIONAL,   -- Need OR
    sib1-BR-r16                             ENUMERATED {supported}      OPTIONAL,   -- Need OR
    ...
}

CarrierFreqsGERAN-NB-r16 ::=            SEQUENCE {
    carrierFreqs-r16                        CarrierFreqsGERAN,
    ec-GSM-IOT-r16                          ENUMERATED {supported}      OPTIONAL,   -- Need OR
    peo-r16                                 ENUMERATED {supported}      OPTIONAL,   -- Need OR
    ...
}


SystemInformationBlockType31-NB-r17 ::= SEQUENCE {
    servingSatelliteInfo-r17        ServingSatelliteInfo-r17,
    lateNonCriticalExtension        OCTET STRING                    OPTIONAL,
    ...
}

SystemInformationBlockType32-NB-r17 ::= SEQUENCE {
    satelliteInfoList-r17               SatelliteInfoList-r17   OPTIONAL,   -- Need OR
    lateNonCriticalExtension            OCTET STRING                    OPTIONAL,
    ...,
    [[  satelliteInfoList-v1800         SatelliteInfoList-v1800 OPTIONAL    -- Need OR
    ]]
}

SystemInformationBlockType33-NB-r18 ::= SEQUENCE {
    neighSatelliteInfoList-r18      NeighSatelliteInfoList-r18      OPTIONAL,   -- Need OR
    neighValidityDuration-r18       ENUMERATED {s5, s10, s15, s20, s25, s30, s35, s40,
                                                s45, s50, s55, s60, s120, s180, s240, s900}
                                                                    OPTIONAL,   -- Need OP  lateNonCriticalExtension        OCTET STRING                    OPTIONAL,
    ...
}

CarrierConfigDedicated-NB-r13 ::=       SEQUENCE {
    dl-CarrierConfig-r13        DL-CarrierConfigDedicated-NB-r13,
    ul-CarrierConfig-r13        UL-CarrierConfigDedicated-NB-r13
}

DL-CarrierConfigDedicated-NB-r13 ::=    SEQUENCE {
    dl-CarrierFreq-r13                      CarrierFreq-NB-r13,
    downlinkBitmapNonAnchor-r13             CHOICE {
        useNoBitmap-r13                         NULL,
        useAnchorBitmap-r13                     NULL,
        explicitBitmapConfiguration-r13         DL-Bitmap-NB-r13,
        spare                                   NULL
    }       OPTIONAL,   -- Need ON
    dl-GapNonAnchor-r13                     CHOICE {
        useNoGap-r13                            NULL,
        useAnchorGapConfig-r13                  NULL,
        explicitGapConfiguration-r13            DL-GapConfig-NB-r13,
        spare                                   NULL
    }       OPTIONAL,   -- Need ON
    inbandCarrierInfo-r13                   SEQUENCE {
        samePCI-Indicator-r13                   CHOICE  {
            samePCI-r13                             SEQUENCE {
                indexToMidPRB-r13                       INTEGER (-55..54)
            },
            differentPCI-r13                        SEQUENCE {
                eutra-NumCRS-Ports-r13                  ENUMERATED {same, four}
            }
        }                           OPTIONAL,       -- Cond anchor-guardband-or-standalone
        eutraControlRegionSize-r13              ENUMERATED {n1, n2, n3}
    }                               OPTIONAL,       -- Cond non-anchor-inband
    ...,
    [[  nrs-PowerOffsetNonAnchor-v1330      ENUMERATED {dB-12, dB-10, dB-8, dB-6,
                                                        dB-4, dB-2, dB0, dB3}
                                    OPTIONAL    -- Need ON
    ]],
    [[  dl-GapNonAnchor-v1530               DL-GapConfig-NB-v1530   OPTIONAL    -- Cond TDD1
    ]],
    [[  dl-CarrierFreq-v1550                CarrierFreq-NB-v1550    OPTIONAL    -- Cond TDD1
    ]]
}

UL-CarrierConfigDedicated-NB-r13 ::=    SEQUENCE {
    ul-CarrierFreq-r13          CarrierFreq-NB-r13      OPTIONAL,   -- Need OP
    ...,
    [[  tdd-UL-DL-AlignmentOffset-r15       TDD-UL-DL-AlignmentOffset-NB-r15        OPTIONAL        -- Cond TDD
    ]]
}

CarrierFreq-NB-r13 ::=      SEQUENCE {
    carrierFreq-r13             ARFCN-ValueEUTRA-r9,
    carrierFreqOffset-r13       ENUMERATED {
                                    v-10, v-9, v-8, v-7, v-6, v-5, v-4, v-3, v-2, v-1, v-0dot5,
                                    v0, v1, v2, v3, v4, v5, v6, v7, v8, v9
                                    }   OPTIONAL    -- Need ON
}

CarrierFreq-NB-v1550    ::=     SEQUENCE {
    carrierFreqOffset-v1550     ENUMERATED {v-8dot5, v-4dot5, v3dot5, v7dot5}
}

ChannelRasterOffset-NB-r13 ::= ENUMERATED {khz-7dot5, khz-2dot5, khz2dot5, khz7dot5}

DL-Bitmap-NB-r13 ::=            CHOICE {
    subframePattern10-r13           BIT STRING (SIZE (10)),
    subframePattern40-r13           BIT STRING (SIZE (40))
}

DL-CarrierConfigCommon-NB-r14 ::=   SEQUENCE {
    dl-CarrierFreq-r14                  CarrierFreq-NB-r13,
    downlinkBitmapNonAnchor-r14         CHOICE {
        useNoBitmap-r14                     NULL,
        useAnchorBitmap-r14                 NULL,
        explicitBitmapConfiguration-r14     DL-Bitmap-NB-r13
    },
    dl-GapNonAnchor-r14                 CHOICE {
        useNoGap-r14                        NULL,
        useAnchorGapConfig-r14              NULL,
        explicitGapConfiguration-r14        DL-GapConfig-NB-r13
    },
    inbandCarrierInfo-r14               SEQUENCE {
        samePCI-Indicator-r14               CHOICE  {
            samePCI-r14                         SEQUENCE {
                indexToMidPRB-r14                   INTEGER (-55..54)
            },
            differentPCI-r14                    SEQUENCE {
                eutra-NumCRS-Ports-r14              ENUMERATED {same, four}
            }
        }   OPTIONAL,       -- Cond anchor-guardband-or-standalone
        eutraControlRegionSize-r14          ENUMERATED {n1, n2, n3}
    }   OPTIONAL,       -- Cond non-anchor-inband
    nrs-PowerOffsetNonAnchor-r14        ENUMERATED {dB-12, dB-10, dB-8, dB-6,
                                                    dB-4, dB-2, dB0, dB3}   DEFAULT dB0,
    ...,
    [[  dl-GapNonAnchor-v1530           DL-GapConfig-NB-v1530   OPTIONAL    -- Cond TDD
    ]],
    [[  dl-CarrierFreq-v1550            CarrierFreq-NB-v1550    OPTIONAL    -- Cond TDD
    ]]
}


DL-GapConfig-NB-r13 ::=     SEQUENCE {
    dl-GapThreshold-r13         ENUMERATED {n32, n64, n128, n256},
    dl-GapPeriodicity-r13       ENUMERATED {sf64, sf128, sf256, sf512},
    dl-GapDurationCoeff-r13     ENUMERATED {oneEighth, oneFourth, threeEighth, oneHalf}
}

DL-GapConfig-NB-v1530   ::= SEQUENCE {
    dl-GapPeriodicity-v1530     ENUMERATED {sf1024}
}

GWUS-Config-NB-r16 ::=          SEQUENCE {
    groupAlternation-r16            ENUMERATED {true}           OPTIONAL, -- Need OR
    commonSequence-r16              ENUMERATED {g0, g126}       OPTIONAL, -- Need OR
    timeParameters-r16              WUS-Config-NB-r15           OPTIONAL, -- Cond noWUSr15
    resourceConfigDRX-r16           GWUS-ResourceConfig-NB-r16,
    resourceConfig-eDRX-Short-r16   GWUS-ResourceConfig-NB-r16  OPTIONAL, -- Need OP
    resourceConfig-eDRX-Long-r16    GWUS-ResourceConfig-NB-r16  OPTIONAL, -- Cond timeOffset
    probThreshList-r16              GWUS-ProbThreshList-NB-r16  OPTIONAL, -- Cond probabilityBased
    ...
}

GWUS-ResourceConfig-NB-r16 ::=  SEQUENCE {
    resourcePosition-r16            ENUMERATED {primary, secondary},
    numGroupsList-r16               GWUS-NumGroupsList-NB-r16           OPTIONAL,   -- Need OP
    groupsForServiceList-r16        GWUS-GroupsForServiceList-NB-r16
                                                            OPTIONAL    -- Cond probabilityBased
}

GWUS-ProbThreshList-NB-r16 ::=          SEQUENCE (SIZE (1..maxGWUS-ProbThresholds-NB-r16)) OF
                                            GWUS-Paging-ProbThresh-NB-r16

GWUS-Paging-ProbThresh-NB-r16 ::=       ENUMERATED {p20, p30, p40, p50, p60, p70, p80, p90}

GWUS-NumGroupsList-NB-r16 ::=               SEQUENCE (SIZE (1..maxGWUS-Resources-NB-r16)) OF
                                            GWUS-NumGroups-NB-r16

GWUS-NumGroups-NB-r16 ::=                   ENUMERATED {n1, n2, n4, n8}

GWUS-GroupsForServiceList-NB-r16 ::=    SEQUENCE (SIZE (1..maxGWUS-ProbThresholds-NB-r16)) OF
                                            INTEGER (1..maxGWUS-Groups-1-NB-r16)

LogicalChannelConfig-NB-r13 ::=     SEQUENCE {
    priority-r13                        INTEGER (1..16)         OPTIONAL,       -- Cond UL
    logicalChannelSR-Prohibit-r13       BOOLEAN                 OPTIONAL,       -- Need ON
    ...
}

MAC-MainConfig-NB-r13 ::=           SEQUENCE {
    ul-SCH-Config-r13                   SEQUENCE {
        periodicBSR-Timer-r13               PeriodicBSR-Timer-NB-r13        OPTIONAL,   -- Need ON
        retxBSR-Timer-r13                   RetxBSR-Timer-NB-r13
    }                                                                   OPTIONAL,   -- Need ON
    drx-Config-r13                      DRX-Config-NB-r13               OPTIONAL,   -- Need ON
    timeAlignmentTimerDedicated-r13     TimeAlignmentTimer,
    logicalChannelSR-Config-r13         CHOICE {
        release                             NULL,
        setup                               SEQUENCE {
            logicalChannelSR-ProhibitTimer-r13  ENUMERATED {
                                                    pp2, pp8, pp32, pp128, pp512,
                                                    pp1024, pp2048, spare}
        }
    }                                                                   OPTIONAL,   -- Need ON
    ...,
    [[  rai-Activation-r14                      ENUMERATED {true}           OPTIONAL,   -- Need OR
        dataInactivityTimerConfig-r14   CHOICE {
            release                             NULL,
            setup                               SEQUENCE {
                dataInactivityTimer-r14             DataInactivityTimer-r14
            }
        }                                                               OPTIONAL    -- Need ON
    ]],
    [[  drx-Cycle-v1430                 ENUMERATED {
                                    sf1280, sf2560, sf5120, sf10240}    OPTIONAL    -- Need ON
    ]],
    [[  ra-CFRA-Config-r14              ENUMERATED {true}               OPTIONAL    -- Need ON
    ]],
    [[  offsetThresholdTA-r17               SetupRelease {OffsetThresholdTA-NB-r17}
                                                                        OPTIONAL    --  Need ON
    ]]
}

PeriodicBSR-Timer-NB-r13 ::=        ENUMERATED {
                                        pp2, pp4, pp8, pp16, pp64, pp128, infinity, spare}

RetxBSR-Timer-NB-r13 ::=            ENUMERATED {
                                        pp4, pp16, pp64, pp128, pp256, pp512, infinity, spare}

DRX-Config-NB-r13 ::=               CHOICE {
    release                             NULL,
    setup                               SEQUENCE {
        onDurationTimer-r13                 ENUMERATED {
                                                pp1, pp2, pp3, pp4, pp8, pp16, pp32, spare},
        drx-InactivityTimer-r13             ENUMERATED {
                                                pp0, pp1, pp2, pp3, pp4, pp8, pp16, pp32},
        drx-RetransmissionTimer-r13         ENUMERATED {
                                                pp0, pp1, pp2, pp4, pp6, pp8, pp16, pp24,
                                                pp33, spare7, spare6, spare5,
                                                spare4, spare3, spare2, spare1},
        drx-Cycle-r13                       ENUMERATED {
                                                sf256, sf512, sf1024, sf1536, sf2048, sf3072,
                                                sf4096, sf4608, sf6144, sf7680, sf8192, sf9216,
                                                spare4, spare3, spare2, spare1},
        drx-StartOffset-r13                 INTEGER (0..255),
        drx-ULRetransmissionTimer-r13       ENUMERATED {
                                                pp0, pp1, pp2, pp4, pp6, pp8, pp16, pp24,
                                                pp33, pp40, pp64, pp80, pp96,
                                                pp112, pp128, pp160, pp320}
    }
}

OffsetThresholdTA-NB-r17 ::=        ENUMERATED {
                                            ms0dot5, ms1, ms2, ms3, ms4, ms5, ms6 ,ms7,
                                            ms8, ms9, ms10, ms11, ms12, ms13, ms14, ms15}

NPDCCH-ConfigDedicated-NB-r13 ::=   SEQUENCE {
    npdcch-NumRepetitions-r13           ENUMERATED {r1, r2, r4, r8, r16, r32, r64, r128,
                                                    r256, r512, r1024, r2048,
                                                    spare4, spare3, spare2, spare1},
    npdcch-StartSF-USS-r13              ENUMERATED {v1dot5, v2, v4, v8, v16, v32, v48, v64},
    npdcch-Offset-USS-r13               ENUMERATED {zero, oneEighth, oneFourth, threeEighth}
}

NPDCCH-ConfigDedicated-NB-v1530 ::= SEQUENCE {
    npdcch-StartSF-USS-v1530            ENUMERATED {v96, v128}
}


NPDSCH-ConfigCommon-NB-r13 ::=  SEQUENCE {
    nrs-Power-r13                   INTEGER (-60..50)
}

NPDSCH-ConfigDedicated-NB-r16 ::=   SEQUENCE {
    npdsch-MultiTB-Config-r16           NPDSCH-MultiTB-Config-NB-r16    OPTIONAL    -- Cond twoHARQ
}

NPDSCH-MultiTB-Config-NB-r16 ::=    SEQUENCE {
    multiTB-Config-r16                  ENUMERATED {interleaved, nonInterleaved},
    harq-AckBundling-r16                ENUMERATED {true}       OPTIONAL    -- Cond interleaved
}

NPDSCH-ConfigDedicated-NB-v1710 ::= SEQUENCE {
    npdsch-16QAM-Config-r17         SetupRelease {NPDSCH-16QAM-Config-NB-r17}
}

NPDSCH-ConfigDedicated-NB-v1800 ::=     SEQUENCE {
    downlinkHARQ-FeedbackDisabledBitmap-NB-r18
        SetupRelease {DownlinkHARQ-FeedbackDisabledBitmap-NB-r18}       OPTIONAL,   -- Need ON
    downlinkHARQ-FeedbackDisabledDCI-NB-r18 ENUMERATED {true}           OPTIONAL    -- Need OR
}

NPDSCH-16QAM-Config-NB-r17 ::=SEQUENCE{
    nrs-PowerRatio-r17          ENUMERATED {dB-6, dB-4dot77, dB-3, dB-1dot77, dB0, dB1, dB2, dB3}   OPTIONAL,   -- Need OR
    nrs-PowerRatioWithCRS-r17   ENUMERATED {dB-6, dB-4dot77, dB-3, dB-1dot77, dB0, dB1, dB2, dB3}   OPTIONAL    -- Cond InBand
}

DownlinkHARQ-FeedbackDisabledBitmap-NB-r18 ::=  BIT STRING (SIZE(2))

NPRACH-ConfigSIB-NB-r13 ::=         SEQUENCE {
    nprach-CP-Length-r13                ENUMERATED {us66dot7, us266dot7},
    rsrp-ThresholdsPrachInfoList-r13    RSRP-ThresholdsNPRACH-InfoList-NB-r13   OPTIONAL,   -- Need OR
    nprach-ParametersList-r13       NPRACH-ParametersList-NB-r13
}

NPRACH-ConfigSIB-NB-v1330 ::=       SEQUENCE {
    nprach-ParametersList-v1330         NPRACH-ParametersList-NB-v1330
}

NPRACH-ConfigSIB-NB-v1450 ::=       SEQUENCE {
    maxNumPreambleAttemptCE-r14         ENUMERATED {n3, n4, n5, n6, n7, n8, n10, spare1}
}

NPRACH-ConfigSIB-NB-v1530 ::=       SEQUENCE {
    tdd-Parameters-r15                  SEQUENCE {
        nprach-PreambleFormat-r15           ENUMERATED {
                                                fmt0, fmt1, fmt2, fmt0-a, fmt1-a},
        dummy                               ENUMERATED {
                                                n1, n2, n4, n8, n16, n32, n64, n128,
                                                n256, n512, n1024},
        nprach-ParametersListTDD-r15        NPRACH-ParametersListTDD-NB-r15
    }   OPTIONAL,       -- Cond TDD
    fmt2-Parameters-r15                 SEQUENCE {
        nprach-ParametersListFmt2-r15       NPRACH-ParametersListFmt2-NB-r15 OPTIONAL,  -- Need OR
        nprach-ParametersListFmt2EDT-r15    NPRACH-ParametersListFmt2-NB-r15 OPTIONAL   -- Cond EDT2
    }   OPTIONAL,       -- Need OR
    edt-Parameters-r15                  SEQUENCE {
        edt-SmallTBS-Subset-r15             ENUMERATED {true}               OPTIONAL,   -- Need OR
        edt-TBS-InfoList-r15                EDT-TBS-InfoList-NB-r15,
        nprach-ParametersListEDT-r15        NPRACH-ParametersList-NB-r14    OPTIONAL    -- Need OR
    }   OPTIONAL        -- Cond EDT1
}

NPRACH-ConfigSIB-NB-v1550 ::=       SEQUENCE {
    tdd-Parameters-v1550                SEQUENCE {
        nprach-ParametersListTDD-v1550      NPRACH-ParametersListTDD-NB-v1550
    }
}

NPRACH-ParametersList-NB-r13 ::=    SEQUENCE (SIZE (1.. maxNPRACH-Resources-NB-r13)) OF NPRACH-Parameters-NB-r13

NPRACH-ParametersList-NB-v1330 ::=  SEQUENCE (SIZE (1.. maxNPRACH-Resources-NB-r13)) OF NPRACH-Parameters-NB-v1330

NPRACH-Parameters-NB-r13::=         SEQUENCE {
    nprach-Periodicity-r13                  ENUMERATED {ms40, ms80, ms160, ms240,
                                                        ms320, ms640, ms1280, ms2560},
    nprach-StartTime-r13                    ENUMERATED {ms8, ms16, ms32, ms64,
                                                        ms128, ms256, ms512, ms1024},
    nprach-SubcarrierOffset-r13             ENUMERATED {n0, n12, n24, n36, n2, n18, n34, spare1},
    nprach-NumSubcarriers-r13               ENUMERATED {n12, n24, n36, n48},
    nprach-SubcarrierMSG3-RangeStart-r13    ENUMERATED {zero, oneThird, twoThird, one},
    maxNumPreambleAttemptCE-r13             ENUMERATED {n3, n4, n5, n6, n7, n8, n10, spare1},
    numRepetitionsPerPreambleAttempt-r13    ENUMERATED {n1, n2, n4, n8, n16, n32, n64, n128},
    npdcch-NumRepetitions-RA-r13            ENUMERATED {r1, r2, r4, r8, r16, r32, r64, r128,
                                                        r256, r512, r1024, r2048,
                                                        spare4, spare3, spare2, spare1},
    npdcch-StartSF-CSS-RA-r13               ENUMERATED {v1dot5, v2, v4, v8, v16, v32, v48, v64},
    npdcch-Offset-RA-r13                    ENUMERATED {zero, oneEighth, oneFourth, threeEighth}
}

NPRACH-Parameters-NB-v1330 ::=      SEQUENCE {
    nprach-NumCBRA-StartSubcarriers-r13     ENUMERATED {n8, n10, n11, n12, n20, n22, n23, n24,
                                                        n32, n34, n35, n36, n40, n44, n46, n48}
}

NPRACH-ParametersList-NB-r14 ::=        SEQUENCE (SIZE (1.. maxNPRACH-Resources-NB-r13)) OF
                                            NPRACH-Parameters-NB-r14

NPRACH-Parameters-NB-r14 ::=            SEQUENCE {
    nprach-Parameters-r14                   SEQUENCE {
        nprach-Periodicity-r14                  ENUMERATED {ms40, ms80, ms160, ms240,
                                                            ms320, ms640, ms1280, ms2560}
                                                    OPTIONAL,   -- NEED OP
        nprach-StartTime-r14                    ENUMERATED {ms8, ms16, ms32, ms64,
                                                            ms128, ms256, ms512, ms1024}
                                                    OPTIONAL,   -- NEED OP
        nprach-SubcarrierOffset-r14             ENUMERATED {n0, n12, n24, n36, n2, n18, n34, spare1}
                                                    OPTIONAL,   -- NEED OP
        nprach-NumSubcarriers-r14               ENUMERATED {n12, n24, n36, n48}
                                                    OPTIONAL,   -- NEED OP
        nprach-SubcarrierMSG3-RangeStart-r14    ENUMERATED {zero, oneThird, twoThird, one}
                                                    OPTIONAL,   -- NEED OP
        npdcch-NumRepetitions-RA-r14            ENUMERATED {r1, r2, r4, r8, r16, r32, r64, r128,
                                                            r256, r512, r1024, r2048,
                                                            spare4, spare3, spare2, spare1}
                                                    OPTIONAL,   -- NEED OP
        npdcch-StartSF-CSS-RA-r14               ENUMERATED {v1dot5, v2, v4, v8, v16, v32, v48, v64}
                                                        OPTIONAL,   -- NEED OP
        npdcch-Offset-RA-r14                    ENUMERATED {zero, oneEighth, oneFourth, threeEighth}
                                                    OPTIONAL,   -- NEED OP
        nprach-NumCBRA-StartSubcarriers-r14     ENUMERATED {n8, n10, n11, n12, n20, n22, n23, n24,
                                                            n32, n34, n35, n36, n40, n44, n46, n48}
                                                    OPTIONAL,   -- NEED OP
        npdcch-CarrierIndex-r14                 INTEGER (1..maxNonAnchorCarriers-NB-r14)
                                                    OPTIONAL,   -- Need OP
        ...
    }   OPTIONAL    -- Need OR
}

NPRACH-ParametersListTDD-NB-r15 ::= SEQUENCE (SIZE (1.. maxNPRACH-Resources-NB-r13)) OF
                                            NPRACH-ParametersTDD-NB-r15

NPRACH-ParametersTDD-NB-r15 ::=     SEQUENCE {
    nprach-Parameters-r15                   SEQUENCE {
        nprach-Periodicity-r15                  ENUMERATED {ms80, ms160, ms320, ms640,
                                                            ms1280, ms2560, ms5120, ms10240}
                                                    OPTIONAL,   -- NEED OP
        nprach-StartTime-r15                    ENUMERATED {ms10, ms20, ms40, ms80,
                                                            ms160, ms320, ms640, ms1280,
                                                            ms2560, ms5120, spare6, spare5,
                                                            spare4, spare3, spare2, spare1}
                                                    OPTIONAL,   -- NEED OP
        nprach-SubcarrierOffset-r15             ENUMERATED {n0, n12, n24, n36, n2, n18, n34, spare1}
                                                    OPTIONAL,   -- NEED OP
        nprach-NumSubcarriers-r15               ENUMERATED {n12, n24, n36, n48}
                                                    OPTIONAL,   -- NEED OP
        nprach-SubcarrierMSG3-RangeStart-r15    ENUMERATED {zero, oneThird, twoThird, one}
                                                    OPTIONAL,   -- NEED OP
        npdcch-NumRepetitions-RA-r15            ENUMERATED {r1, r2, r4, r8, r16, r32, r64, r128,
                                                            r256, r512, r1024, r2048,
                                                            spare4, spare3, spare2, spare1}
                                                    OPTIONAL,   -- NEED OP
        npdcch-StartSF-CSS-RA-r15               ENUMERATED {v4, v8, v16, v32, v48, v64, v96, v128}
                                                        OPTIONAL,   -- NEED OP
        npdcch-Offset-RA-r15                    ENUMERATED {zero, oneEighth, oneFourth, threeEighth}
                                                    OPTIONAL,   -- NEED OP
        nprach-NumCBRA-StartSubcarriers-r15     ENUMERATED {n8, n10, n11, n12, n20, n22, n23, n24,
                                                            n32, n34, n35, n36, n40, n44, n46, n48}
                                                    OPTIONAL,   -- NEED OP
        ...
    }   OPTIONAL    -- Need OR
}

NPRACH-ParametersListTDD-NB-v1550 ::=   SEQUENCE (SIZE (1.. maxNPRACH-Resources-NB-r13)) OF
                                                NPRACH-ParametersTDD-NB-v1550

NPRACH-ParametersTDD-NB-v1550 ::=   SEQUENCE {
    maxNumPreambleAttemptCE-v1550           ENUMERATED {n3, n4, n5, n6, n7, n8, n10, spare1},
    numRepetitionsPerPreambleAttempt-v1550  ENUMERATED {n1, n2, n4, n8, n16, n32, n64, n128,
                                                            n256, n512, n1024}
}

NPRACH-ParametersListFmt2-NB-r15 ::=    SEQUENCE (SIZE (1.. maxNPRACH-Resources-NB-r13)) OF NPRACH-ParametersFmt2-NB-r15

NPRACH-ParametersFmt2-NB-r15 ::=        SEQUENCE {
    nprach-Parameters-r15                   SEQUENCE {
        nprach-Periodicity-r15                  ENUMERATED {ms40, ms80, ms160, ms320,
                                                            ms640, ms1280, ms2560, ms5120}
                                                    OPTIONAL,   -- NEED OP
        nprach-StartTime-r15                    ENUMERATED {ms8, ms16, ms32, ms64,
                                                            ms128, ms256, ms512, ms1024}
                                                    OPTIONAL,   -- NEED OP
        nprach-SubcarrierOffset-r15             ENUMERATED {n0, n36, n72, n108, n6, n54, n102, n42,
                                                            n78, n90, n12, n24, n48, n84, n60, n18}
                                                    OPTIONAL,   -- NEED OP
        nprach-NumSubcarriers-r15               ENUMERATED {n36, n72, n108, n144}
                                                    OPTIONAL,   -- NEED OP
        nprach-SubcarrierMSG3-RangeStart-r15    ENUMERATED {zero, oneThird, twoThird, one}
                                                    OPTIONAL,   -- NEED OP
        npdcch-NumRepetitions-RA-r15            ENUMERATED {r1, r2, r4, r8, r16, r32, r64, r128,
                                                            r256, r512, r1024, r2048,
                                                            spare4, spare3, spare2, spare1}
                                                    OPTIONAL,   -- NEED OP
        npdcch-StartSF-CSS-RA-r15               ENUMERATED {v1dot5, v2, v4, v8, v16, v32, v48, v64}
                                                        OPTIONAL,   -- NEED OP
        npdcch-Offset-RA-r15                    ENUMERATED {zero, oneEighth, oneFourth, threeEighth}
                                                    OPTIONAL,   -- NEED OP
        nprach-NumCBRA-StartSubcarriers-r15     ENUMERATED {
                                                    n24, n30, n33, n36, n60, n66, n69, n72,
                                                    n96, n102, n105, n108, n120, n132, n138, n144}
                                                    OPTIONAL,   -- NEED OP
        npdcch-CarrierIndex-r15                 INTEGER (1..maxNonAnchorCarriers-NB-r14)
                                                    OPTIONAL,   -- Need OP
        ...
    }   OPTIONAL    -- Need OR
}

NPRACH-TxDurationFmt01-NB-r17 ::=   SEQUENCE {
    nprach-TxDurationFmt01-r17      ENUMERATED {n2, n4, n8, n16, n32, n64}
}

NPRACH-TxDurationFmt2-NB-r17 ::=    SEQUENCE {
    nprach-TxDurationFmt2-r17       ENUMERATED {n1, n2, n4, n8, n16}
}

RSRP-ThresholdsNPRACH-InfoList-NB-r13 ::= SEQUENCE (SIZE(1..2)) OF RSRP-Range

EDT-TBS-InfoList-NB-r15 ::= SEQUENCE (SIZE (1.. maxNPRACH-Resources-NB-r13)) OF EDT-TBS-NB-r15

EDT-TBS-NB-r15 ::=  SEQUENCE {
    edt-SmallTBS-Enabled-r15        BOOLEAN,
    edt-TBS-r15                     ENUMERATED {b328, b408, b504, b584, b680, b808, b936, b1000}
}

NPUSCH-ConfigCommon-NB-r13 ::=      SEQUENCE {
    ack-NACK-NumRepetitions-Msg4-r13    SEQUENCE (SIZE(1.. maxNPRACH-Resources-NB-r13)) OF
                                                        ACK-NACK-NumRepetitions-NB-r13,
    srs-SubframeConfig-r13              ENUMERATED {
                                            sc0, sc1, sc2, sc3, sc4, sc5, sc6, sc7,
                                            sc8, sc9, sc10, sc11, sc12, sc13, sc14, sc15
                                            }                           OPTIONAL,   -- Need OR
    dmrs-Config-r13                     SEQUENCE {
        threeTone-BaseSequence-r13          INTEGER (0..12)         OPTIONAL,   -- Need OP
        threeTone-CyclicShift-r13           INTEGER (0..2),
        sixTone-BaseSequence-r13            INTEGER (0..14)         OPTIONAL,   -- Need OP
        sixTone-CyclicShift-r13             INTEGER (0..3),
        twelveTone-BaseSequence-r13         INTEGER (0..30)         OPTIONAL    -- Need OP
    }       OPTIONAL,   -- Need OR
    ul-ReferenceSignalsNPUSCH-r13       UL-ReferenceSignalsNPUSCH-NB-r13
}

UL-ReferenceSignalsNPUSCH-NB-r13 ::=    SEQUENCE {
    groupHoppingEnabled-r13                 BOOLEAN,
    groupAssignmentNPUSCH-r13               INTEGER (0..29)
}

NPUSCH-ConfigDedicated-NB-r13 ::=   SEQUENCE {
    ack-NACK-NumRepetitions-r13         ACK-NACK-NumRepetitions-NB-r13  OPTIONAL,   -- Need ON
    npusch-AllSymbols-r13               BOOLEAN                         OPTIONAL,   -- Cond SRS
    groupHoppingDisabled-r13            ENUMERATED {true}               OPTIONAL    -- Need OR
}

NPUSCH-ConfigDedicated-NB-v1610 ::= SEQUENCE {
    npusch-MultiTB-Config-r16           ENUMERATED {interleaved, nonInterleaved}
}

NPUSCH-ConfigDedicated-NB-v1700 ::= SEQUENCE {
    npusch-16QAM-Config-r17     ENUMERATED {true}   OPTIONAL    -- Need OR
}

NPUSCH-ConfigDedicated-NB-v1800 ::=     SEQUENCE {
    uplinkHARQ-Mode-r18     SetupRelease {UplinkHARQ-Mode-NB-r18}
}

NPUSCH-TxDuration-NB-r17 ::=    SEQUENCE {
    npusch-TxDuration-r17           ENUMERATED {ms2, ms4, ms8, ms16, ms32, ms64, ms128, ms256}
}

ACK-NACK-NumRepetitions-NB-r13  ::= ENUMERATED {r1, r2, r4, r8, r16, r32, r64, r128}

UplinkHARQ-Mode-NB-r18 ::=  BIT STRING (SIZE(2))

PDCP-Config-NB-r13 ::=      SEQUENCE {
    discardTimer-r13            ENUMERATED {
                                    ms5120, ms10240, ms20480, ms40960,
                                    ms81920, infinity, spare2, spare1
                                    }   OPTIONAL,           -- Cond Setup
    headerCompression-r13       CHOICE {
        notUsed                     NULL,
        rohc                        SEQUENCE {
            maxCID-r13                  INTEGER (1..16383)              DEFAULT 15,
            profiles-r13                SEQUENCE {
                profile0x0002               BOOLEAN,
                profile0x0003               BOOLEAN,
                profile0x0004               BOOLEAN,
                profile0x0006               BOOLEAN,
                profile0x0102               BOOLEAN,
                profile0x0103               BOOLEAN,
                profile0x0104               BOOLEAN
            },
            ...
        }
    },
    ...,
    [[  cipheringDisabled-r16       ENUMERATED {true}       OPTIONAL    -- Cond ConnectedTo5GC
    ]]
}

PhysicalConfigDedicated-NB-r13 ::=  SEQUENCE {
    carrierConfigDedicated-r13          CarrierConfigDedicated-NB-r13       OPTIONAL,   -- Need ON
    npdcch-ConfigDedicated-r13          NPDCCH-ConfigDedicated-NB-r13       OPTIONAL,   -- Need ON
    npusch-ConfigDedicated-r13          NPUSCH-ConfigDedicated-NB-r13       OPTIONAL,   -- Need ON
    uplinkPowerControlDedicated-r13     UplinkPowerControlDedicated-NB-r13  OPTIONAL,   -- Need ON
    ...,
    [[  twoHARQ-ProcessesConfig-r14     ENUMERATED {true}   OPTIONAL    -- Need OR
    ]],
    [[  interferenceRandomisationConfig-r14 ENUMERATED {true}   OPTIONAL    -- Need OR
    ]],
    [[  npdcch-ConfigDedicated-v1530    NPDCCH-ConfigDedicated-NB-v1530     OPTIONAL    -- Cond TDD
    ]],
    [[  additionalTxSIB1-Config-v1540   ENUMERATED {true}   OPTIONAL    -- Cond additionalSIB1
    ]],
    [[  npusch-ConfigDedicated-v1610        NPUSCH-ConfigDedicated-NB-v1610
                                                                    OPTIONAL,   -- Cond twoHARQ
        npdsch-ConfigDedicated-r16          NPDSCH-ConfigDedicated-NB-r16
                                                                    OPTIONAL,   -- Need ON
        resourceReservationConfigDL-r16     SetupRelease {ResourceReservationConfig-NB-r16}
                                                                        OPTIONAL,   -- Cond dl-NonAnchor
        resourceReservationConfigUL-r16     SetupRelease {ResourceReservationConfig-NB-r16}
                                                                    OPTIONAL    -- Cond ul-NonAnchor
    ]],
    [[  ntn-ConfigDedicated-r17             SEQUENCE {
            npusch-TxDuration-r17                   SetupRelease {NPUSCH-TxDuration-NB-r17}
        } OPTIONAL, -- Cond NTN
        npdsch-ConfigDedicated-v1700    NPDSCH-ConfigDedicated-NB-v1710 OPTIONAL,   -- Need ON
        uplinkPowerControlDedicated-v1700   UplinkPowerControlDedicated-NB-v1700        OPTIONAL -- Cond npusch-16QAM
    ]],
    [[
    uplinkSegmentedPrecompensationGap-r17  ENUMERATED {sym1,sl1,sl2}    OPTIONAL  -- Need OR
    ]],
    [[  npusch-ConfigDedicated-v1740    NPUSCH-ConfigDedicated-NB-v1700 OPTIONAL    -- Need ON
    ]],
    [[  npdsch-ConfigDedicated-v1800    NPDSCH-ConfigDedicated-NB-v1800 OPTIONAL,   -- Need ON
        npusch-ConfigDedicated-v1800    NPUSCH-ConfigDedicated-NB-v1800 OPTIONAL    -- Need ON
    ]]
}

PUR-Config-NB-r16   ::=             SEQUENCE {
    pur-ConfigID-r16                    PUR-ConfigID-NB-r16             OPTIONAL,   --Need OR
    pur-TimeAlignmentTimer-r16          INTEGER (1..8)              OPTIONAL,   --Need OR
    pur-NRSRP-ChangeThreshold-r16       SetupRelease {PUR-NRSRP-ChangeThreshold-NB-r16}
                                                                        OPTIONAL,   --Need ON
    pur-ImplicitReleaseAfter-r16        ENUMERATED {n2, n4, n8, spare}  OPTIONAL,   --Need OR
    pur-RNTI-r16                        C-RNTI                          OPTIONAL,   --Need ON
    pur-ResponseWindowTimer-r16         ENUMERATED {pp1, pp2, pp3, pp4, pp8, pp16, pp32, pp64}
                                                                        OPTIONAL,   --Need ON
    pur-StartTimeParameters-r16         SEQUENCE {
        periodicityAndOffset-r16            PUR-PeriodicityAndOffset-NB-r16,
        startSFN-r16                        INTEGER (0..1023),
        startSubframe-r16                   INTEGER (0..9),
        hsfn-LSB-Info-r16                   BIT STRING (SIZE(1))
    }                                                                   OPTIONAL,   --Need ON
    pur-NumOccasions-r16                ENUMERATED {one, infinite},
    pur-PhysicalConfig-r16              SEQUENCE {
        carrierConfig-r16                   CarrierConfigDedicated-NB-r13,
        npusch-NumRUsIndex-r16              INTEGER (0..7),
        npusch-NumRepetitionsIndex-r16      INTEGER (0..7),
        npusch-SubCarrierSetIndex-r16       CHOICE {
            khz15                               INTEGER (0..18),
            khz3dot75                           INTEGER (0..47)
        },
        npusch-MCS-r16                      CHOICE {
            singleTone                          INTEGER (0..10),
            multiTone                           INTEGER (0..13)
        },
        p0-UE-NPUSCH-r16                    INTEGER (-8..7),
        alpha-r16                           ENUMERATED {al0, al04, al05, al06,
                                                        al07, al08, al09, al1},
        npusch-CyclicShift-r16              ENUMERATED {n0, n6},
        npdcch-Config-r16                   NPDCCH-ConfigDedicated-NB-r13
    }   OPTIONAL,   -- Need ON
    ...,
    [[
        pur-PhysicalConfig-v1650            SEQUENCE {
            ack-NACK-NumRepetitions-r16     ACK-NACK-NumRepetitions-NB-r13
        }                                                       OPTIONAL    --Need ON
    ]],
    [[
        pur-PhysicalConfig-v1700            SEQUENCE {
            pur-UL-16QAM-Config-r17     SetupRelease {PUR-UL-16QAM-Config-NB-r17} OPTIONAL, -- Need ON
            pur-DL-16QAM-Config-r17     SetupRelease {NPDSCH-16QAM-Config-NB-r17} OPTIONAL  -- Need ON
        }               OPTIONAL    -- Need ON
    ]]
}

PUR-NRSRP-ChangeThreshold-NB-r16 ::=    SEQUENCE {
    increaseThresh-r16                      NRSRP-ChangeThresh-NB-r16,
    decreaseThresh-r16                      NRSRP-ChangeThresh-NB-r16   OPTIONAL    --Need OP
}

PUR-UL-16QAM-Config-NB-r17 ::= SEQUENCE {
    uplinkPowerControlDedicated-r17     UplinkPowerControlDedicated-NB-v1700
}

NRSRP-ChangeThresh-NB-r16 ::= ENUMERATED {dB4, dB6, dB8, dB10, dB14, dB18, dB22, dB26, dB30, dB34, spare6, spare5, spare4, spare3, spare2, spare1}

PUR-ConfigID-NB-r16 ::= BIT STRING (SIZE(20))

PUR-PeriodicityAndOffset-NB-r16 ::= CHOICE {
    periodicity8        INTEGER (1..7),
    periodicity16       INTEGER (1..15),
    periodicity32       INTEGER (1..31),
    periodicity64       INTEGER (1..63),
    periodicity128      INTEGER (1..127),
    periodicity256      INTEGER (1..257),
    periodicity512      INTEGER (1..511),
    periodicity1024     INTEGER (1..1023),
    periodicity2048     INTEGER (1..2047),
    periodicity4096     INTEGER (1..4095),
    periodicity8192     INTEGER (1..8191)
}

RACH-ConfigCommon-NB-r13 ::=        SEQUENCE {
    preambleTransMax-CE-r13             PreambleTransMax,
    powerRampingParameters-r13          PowerRampingParameters,
    rach-InfoList-r13                   RACH-InfoList-NB-r13,
    connEstFailOffset-r13               INTEGER (0..15)                 OPTIONAL,   -- Need OP
    ...,
    [[  powerRampingParameters-v1450    PowerRampingParameters-NB-v1450 OPTIONAL    -- Need OR
    ]],
    [[ rach-InfoList-v1530              RACH-InfoList-NB-v1530  OPTIONAL -- Cond EDT
    ]]
}

RACH-InfoList-NB-r13 ::=    SEQUENCE (SIZE (1.. maxNPRACH-Resources-NB-r13)) OF RACH-Info-NB-r13

RACH-InfoList-NB-v1530 ::=  SEQUENCE (SIZE (1.. maxNPRACH-Resources-NB-r13)) OF RACH-Info-NB-v1530

RACH-Info-NB-r13    ::=     SEQUENCE {
    ra-ResponseWindowSize-r13           ENUMERATED {
                                            pp2, pp3, pp4, pp5, pp6, pp7, pp8, pp10},
    mac-ContentionResolutionTimer-r13   ENUMERATED {
                                            pp1, pp2, pp3, pp4, pp8, pp16, pp32, pp64}
}

RACH-Info-NB-v1530 ::=      SEQUENCE {
    mac-ContentionResolutionTimer-r15   ENUMERATED {
                                            pp1, pp2, pp3, pp4, pp8, pp16, pp32, pp64}
}

PowerRampingParameters-NB-v1450 ::=     SEQUENCE {
    preambleInitialReceivedTargetPower-v1450        ENUMERATED {
                                                    dBm-130, dBm-128, dBm-126, dBm-124, dBm-122,
                                                    dBm-88, dBm-86, dBm-84,dBm-82, dBm-80}
                                                    OPTIONAL,   -- Need OR
    powerRampingParametersCE1-r14               SEQUENCE {
        powerRampingStepCE1-r14                     ENUMERATED {dB0, dB2, dB4, dB6},
        preambleInitialReceivedTargetPowerCE1-r14   ENUMERATED {
                                                    dBm-130, dBm-128, dBm-126, dBm-124, dBm-122,
                                                    dBm-120, dBm-118, dBm-116, dBm-114, dBm-112,
                                                    dBm-110, dBm-108, dBm-106, dBm-104, dBm-102,
                                                    dBm-100, dBm-98, dBm-96, dBm-94, dBm-92,
                                                    dBm-90, dBm-88, dBm-86, dBm-84, dBm-82, dBm-80}
    } OPTIONAL  -- Need OR
}

RadioResourceConfigCommonSIB-NB-r13 ::= SEQUENCE {
    rach-ConfigCommon-r13                   RACH-ConfigCommon-NB-r13,
    bcch-Config-r13                         BCCH-Config-NB-r13,
    pcch-Config-r13                         PCCH-Config-NB-r13,
    nprach-Config-r13                       NPRACH-ConfigSIB-NB-r13,
    npdsch-ConfigCommon-r13                 NPDSCH-ConfigCommon-NB-r13,
    npusch-ConfigCommon-r13                 NPUSCH-ConfigCommon-NB-r13,
    dl-Gap-r13                              DL-GapConfig-NB-r13         OPTIONAL,       -- Need OP
    uplinkPowerControlCommon-r13            UplinkPowerControlCommon-NB-r13,
    ...,
    [[  nprach-Config-v1330                 NPRACH-ConfigSIB-NB-v1330   OPTIONAL        -- Need OR
    ]],
    [[  nprach-Config-v1450                 NPRACH-ConfigSIB-NB-v1450   OPTIONAL        -- Cond EnhPowerControl
    ]],
    [[  nprach-Config-v1530                 NPRACH-ConfigSIB-NB-v1530   OPTIONAL,   -- Need OR
        dl-Gap-v1530                        DL-GapConfig-NB-v1530       OPTIONAL,   -- Cond TDD
        wus-Config-r15                      WUS-Config-NB-r15           OPTIONAL    -- Need OR
    ]],
    [[  nprach-Config-v1550                 NPRACH-ConfigSIB-NB-v1550   OPTIONAL    -- Cond TDD1
    ]],
    [[
        gwus-Config-r16                     GWUS-Config-NB-r16          OPTIONAL,   -- Need OR
        nrs-NonAnchorConfig-r16             ENUMERATED {true}           OPTIONAL,   -- Need OR
        ue-SpecificDRX-CycleMin-r16         ENUMERATED {rf32, rf64, rf128, rf256, rf512,
                                                            rf1024}     OPTIONAL    -- Need OR
    ]],
    [[  ntn-ConfigCommon-r17                SEQUENCE {
            ta-Report-r17                   ENUMERATED {enabled}        OPTIONAL,   -- Need OR
            t318-r17                        ENUMERATED {
                                                ms0, ms200, ms500, ms1000, ms2000, ms4000, ms8000},
            nprach-TxDurationFmt01-r17      NPRACH-TxDurationFmt01-NB-r17   OPTIONAL,   -- Need OR
            nprach-TxDurationFmt2-r17       NPRACH-TxDurationFmt2-NB-r17    OPTIONAL,   -- Need OR
            npusch-TxDuration-r17           NPUSCH-TxDuration-NB-r17        OPTIONAL    -- Need OR
        }   OPTIONAL    -- Cond NTN
    ]]
}

BCCH-Config-NB-r13 ::=                  SEQUENCE {
    modificationPeriodCoeff-r13             ENUMERATED {n16, n32, n64, n128}
}

PCCH-Config-NB-r13 ::=                  SEQUENCE {
    defaultPagingCycle-r13                  ENUMERATED {rf128, rf256, rf512, rf1024},
    nB-r13                                  ENUMERATED {
                                                fourT, twoT, oneT, halfT, quarterT, one8thT,
                                                one16thT, one32ndT, one64thT,
                                                one128thT, one256thT, one512thT, one1024thT,
                                                spare3, spare2, spare1},
    npdcch-NumRepetitionPaging-r13          ENUMERATED {
                                                r1, r2, r4, r8, r16, r32, r64, r128,
                                                r256, r512, r1024, r2048,
                                                spare4, spare3, spare2, spare1}
}

RadioResourceConfigDedicated-NB-r13 ::= SEQUENCE {
    srb-ToAddModList-r13                    SRB-ToAddModList-NB-r13         OPTIONAL,   -- Need ON
    drb-ToAddModList-r13                    DRB-ToAddModList-NB-r13         OPTIONAL,   -- Need ON
    drb-ToReleaseList-r13                   DRB-ToReleaseList-NB-r13        OPTIONAL,   -- Need ON
    mac-MainConfig-r13                      CHOICE {
        explicitValue-r13                       MAC-MainConfig-NB-r13,
        defaultValue-r13                        NULL
    }                                                                       OPTIONAL,   -- Need ON
    physicalConfigDedicated-r13             PhysicalConfigDedicated-NB-r13  OPTIONAL,   -- Need ON
    rlf-TimersAndConstants-r13              RLF-TimersAndConstants-NB-r13   OPTIONAL,   -- Need ON
    ...,
    [[  schedulingRequestConfig-r15         SchedulingRequestConfig-NB-r15  OPTIONAL    -- Need ON
    ]],
    [[  newUE-Identity-r16                  C-RNTI                          OPTIONAL    -- Need OP
    ]],
    [[  gnss-AutonomousEnabled-r18          ENUMERATED {true}           OPTIONAL,   -- Need OR
        ul-TransmissionExtensionEnabled-r18 ENUMERATED {true}           OPTIONAL,   -- Need OR
        ul-TransmissionExtensionValue-r18   ENUMERATED {sf500, sf750, sf1280, sf1920,
                                                        sf2560, sf5120, sf10240, spare1}
                                                                        OPTIONAL    -- Need OR
    ]]
}

SRB-ToAddModList-NB-r13 ::=         SEQUENCE (SIZE (1)) OF SRB-ToAddMod-NB-r13

SRB-ToAddMod-NB-r13 ::=             SEQUENCE {
    rlc-Config-r13                      CHOICE {
        explicitValue                       RLC-Config-NB-r13,
        defaultValue                        NULL
    }       OPTIONAL,                                                           -- Cond Setup
    logicalChannelConfig-r13            CHOICE {
        explicitValue                       LogicalChannelConfig-NB-r13,
        defaultValue                        NULL
    }       OPTIONAL,                                                           -- Cond Setup
    ...,
    [[  rlc-Config-v1430                RLC-Config-NB-v1430         OPTIONAL    -- Need ON
    ]],
    [[  rlc-Config-v1700                RLC-Config-NB-v1700     OPTIONAL    -- Need ON
    ]]
}

DRB-ToAddModList-NB-r13 ::=         SEQUENCE (SIZE (1..maxDRB-NB-r13)) OF DRB-ToAddMod-NB-r13

DRB-ToAddMod-NB-r13 ::=             SEQUENCE {
    eps-BearerIdentity-r13              INTEGER (0..15)             OPTIONAL,   -- Cond DRB-Setup-EPC
    drb-Identity-r13                    DRB-Identity,
    pdcp-Config-r13                     PDCP-Config-NB-r13          OPTIONAL,   -- Cond Setup
    rlc-Config-r13                      RLC-Config-NB-r13           OPTIONAL,   -- Cond Setup
    logicalChannelIdentity-r13          INTEGER (3..10)             OPTIONAL,   -- Cond DRB-Setup
    logicalChannelConfig-r13            LogicalChannelConfig-NB-r13 OPTIONAL,   -- Cond Setup
    ...,
    [[  rlc-Config-v1430                RLC-Config-NB-v1430         OPTIONAL    -- Need ON
    ]],
    [[  pdu-Session-r16             PDU-SessionID-NB-r16        OPTIONAL    -- Cond DRB-Setup-5GC
    ]],
    [[  rlc-Config-v1700                RLC-Config-NB-v1700     OPTIONAL    -- Need ON
    ]]
}

PDU-SessionID-NB-r16 ::=            INTEGER (0..255)

DRB-ToReleaseList-NB-r13 ::=        SEQUENCE (SIZE (1..maxDRB-NB-r13)) OF DRB-Identity

ResourceReservationConfig-NB-r16::= SEQUENCE {
    periodicity-r16             ENUMERATED {ms10, ms20, ms40, ms80, ms160, spare3, spare2, spare1},
    startPosition-r16           INTEGER (0..15),
    resourceReservation-r16     CHOICE {
        subframeBitmap-r16          CHOICE {
            subframePattern10ms         BIT STRING (SIZE (10)),
            subframePattern40ms         BIT STRING (SIZE (40))
        },
        slotConfig-r16              SEQUENCE {
            slotBitmap-r16              CHOICE {
                slotPattern10ms             BIT STRING (SIZE (20)),
                slotPattern40ms             BIT STRING (SIZE (80))
            },
            symbolBitmap-r16            CHOICE {
                symbolBitmapFddDl           SEQUENCE {
                    symbolBitmap1-r16           BIT STRING (SIZE (5))   OPTIONAL,   -- Cond Bitmap1
                    symbolBitmap2-r16           BIT STRING (SIZE (5))   OPTIONAL    -- Cond Bitmap2
                },
                symbolBitmapFddUlOrTdd      SEQUENCE {
                    symbolBitmap1-r16           BIT STRING (SIZE (7))   OPTIONAL,   -- Cond Bitmap1
                    symbolBitmap2-r16           BIT STRING (SIZE (7))   OPTIONAL    -- Cond Bitmap2
                }
            }
        }
    },
    ...
}

RLC-Config-NB-r13 ::=   CHOICE  {
    am                      SEQUENCE {
        ul-AM-RLC-r13               UL-AM-RLC-NB-r13,
        dl-AM-RLC-r13               DL-AM-RLC-NB-r13
    },
    ...,
    um-Bi-Directional-r15       NULL,
    um-Uni-Directional-UL-r15   NULL,
    um-Uni-Directional-DL-r15   NULL
}

RLC-Config-NB-v1430 ::= SEQUENCE {
    t-Reordering-r14            T-Reordering        OPTIONAL        -- Cond twoHARQ
}

RLC-Config-NB-v1700 ::= SEQUENCE {
    t-ReorderingExt-r17                 SetupRelease {T-ReorderingExt-r17}
}

UL-AM-RLC-NB-r13 ::=        SEQUENCE {
    t-PollRetransmit-r13        T-PollRetransmit-NB-r13,
    maxRetxThreshold-r13        ENUMERATED {t1, t2, t3, t4, t6, t8, t16, t32}
}

DL-AM-RLC-NB-r13 ::=        SEQUENCE {
    enableStatusReportSN-Gap-r13    ENUMERATED {true}   OPTIONAL
}

T-PollRetransmit-NB-r13 ::= ENUMERATED {
                                    ms250,  ms500,  ms1000, ms2000, ms3000, ms4000,
                                    ms6000, ms10000, ms15000, ms25000, ms40000, ms60000,
                                    ms90000, ms120000, ms180000, ms300000-v1530}



RLF-TimersAndConstants-NB-r13 ::=   CHOICE {
    release                             NULL,
    setup                               SEQUENCE {
        t301-r13                            ENUMERATED {
                                                ms2500, ms4000, ms6000, ms10000,
                                                ms15000, ms25000, ms40000, ms60000},
        t310-r13                            ENUMERATED {
                                                ms0, ms200, ms500, ms1000, ms2000, ms4000, ms8000},
        n310-r13                            ENUMERATED {
                                                n1, n2, n3, n4, n6, n8, n10, n20},
        t311-r13                            ENUMERATED {
                                                ms1000, ms3000, ms5000, ms10000, ms15000,
                                                ms20000, ms30000},
        n311-r13                            ENUMERATED {
                                                n1, n2, n3, n4, n5, n6, n8, n10},
        ...,
        [[ t311-v1350                       ENUMERATED {
                                                ms40000, ms60000, ms90000, ms120000}
                                                        OPTIONAL    -- Need OR
        ]],
        [[  t301-v1530                      ENUMERATED {
                                                ms80000, ms100000, ms120000}
                                                        OPTIONAL,   -- Cond TDD
            t311-v1530                      ENUMERATED {
                                                ms160000, ms200000}
                                                        OPTIONAL    -- Cond TDD
        ]]
    }
}

SchedulingRequestConfig-NB-r15 ::=  SEQUENCE {
    sr-WithHARQ-ACK-Config-r15          ENUMERATED {true}   OPTIONAL,
    sr-WithoutHARQ-ACK-Config-r15           SR-WithoutHARQ-ACK-Config-NB-r15    OPTIONAL,   -- Need ON
    sr-SPS-BSR-Config-r15               SR-SPS-BSR-Config-NB-r15            OPTIONAL,   -- Need ON
    ...,
    [[  sr-WithoutHARQ-ACK-Config-v1700 SR-WithoutHARQ-ACK-Config-NB-v1700  OPTIONAL    -- Need ON
    ]]
}

SR-WithoutHARQ-ACK-Config-NB-r15 ::= CHOICE {
    release                             NULL,
    setup                               SEQUENCE {
        sr-ProhibitTimer-r15                INTEGER (0..7)  OPTIONAL,   -- Need ON
        sr-NPRACH-Resource-r15              SR-NPRACH-Resource-NB-r15   OPTIONAL -- Need ON
    }
}

SR-WithoutHARQ-ACK-Config-NB-v1700  ::= SEQUENCE {
    sr-ProhibitTimerOffset-r17              SetupRelease {SR-ProhibitTimerOffset-NB-r17}                                                                                OPTIONAL -- Need ON
}

SR-NPRACH-Resource-NB-r15       ::= SEQUENCE {
    nprach-CarrierIndex-r15             INTEGER (0..maxNonAnchorCarriers-NB-r14),
    nprach-ResourceIndex-r15            INTEGER (1..maxNPRACH-Resources-NB-r13),
    nprach-SubCarrierIndex-r15          CHOICE {
        nprach-Fmt0Fmt1-r15                 INTEGER (0..47),
        nprach-Fmt2-r15                     INTEGER (0..143)
    },
    p0-SR-r15                           INTEGER (-126..24),
    alpha-r15                           ENUMERATED {al0, al04, al05, al06, al07, al08, al09, al1}}

SR-SPS-BSR-Config-NB-r15 ::= CHOICE {
    release                             NULL,
    setup                               SEQUENCE {
        semiPersistSchedC-RNTI-r15          C-RNTI,
        semiPersistSchedIntervalUL-r15      ENUMERATED {sf128, sf256, sf512, sf1024,
                                                        sf1280, sf2048, sf2560, sf5120}
    }
}

SR-ProhibitTimerOffset-NB-r17 ::=   ENUMERATED {
                                        ms90, ms180, ms270, ms360, ms450, ms540, ms1080, spare}

TDD-Config-NB-r15 ::=                   SEQUENCE {
    subframeAssignment-r15                  ENUMERATED {
                                                sa1, sa2, sa3, sa4, sa5},
    specialSubframePatterns-r15             ENUMERATED {
                                                ssp0, ssp1, ssp2, ssp3, ssp4, ssp5, ssp6, ssp7,
                                                ssp8, ssp9, ssp10, ssp10-CRS-LessDwPTS}
}

TDD-UL-DL-AlignmentOffset-NB-r15 ::=                ENUMERATED {    khz-7dot5, khz0, khz7dot5}


UplinkPowerControlCommon-NB-r13 ::= SEQUENCE {
    p0-NominalNPUSCH-r13                INTEGER (-126..24),
    alpha-r13                           ENUMERATED {al0, al04, al05, al06, al07, al08, al09, al1},
    deltaPreambleMsg3-r13               INTEGER (-1..6)
}

UplinkPowerControlDedicated-NB-r13 ::=  SEQUENCE {
    p0-UE-NPUSCH-r13                        INTEGER (-8..7)
}

UplinkPowerControlDedicated-NB-v1700 ::=    SEQUENCE {
    deltaMCS-Enabled-r17                    ENUMERATED {en0, en1}
}

WUS-Config-NB-r15 ::=           SEQUENCE {
    maxDurationFactor-r15           WUS-MaxDurationFactor-NB-r15,
    numPOs-r15                      ENUMERATED {n1, n2, n4}     DEFAULT n1,
    numDRX-CyclesRelaxed-r15            ENUMERATED {n1, n2, n4, n8},
    timeOffsetDRX-r15               ENUMERATED {ms40, ms80, ms160, ms240},
    timeOffset-eDRX-Short-r15       ENUMERATED {ms40, ms80, ms160, ms240},
    timeOffset-eDRX-Long-r15        ENUMERATED {ms1000, ms2000} OPTIONAL,   -- Need OP
    ...
}

WUS-ConfigPerCarrier-NB-r15 ::= SEQUENCE {
    maxDurationFactor-r15           WUS-MaxDurationFactor-NB-r15
}

WUS-MaxDurationFactor-NB-r15 ::= ENUMERATED {one128th, one64th, one32th, one16th,
                                            oneEighth, oneQuarter, oneHalf}
AdditionalBandInfoList-NB-r14 ::=   SEQUENCE (SIZE (1..maxMultiBands)) OF FreqBandIndicator-NB-r13

FreqBandIndicator-NB-r13 ::=            INTEGER (1.. maxFBI2)

MultiBandInfoList-NB-r13 ::=    SEQUENCE (SIZE (1..maxMultiBands)) OF MultiBandInfo-NB-r13

MultiBandInfo-NB-r13 ::=        SEQUENCE {
    freqBandIndicator-r13           FreqBandIndicator-NB-r13        OPTIONAL,   -- Need OR
    freqBandInfo-r13                NS-PmaxList-NB-r13              OPTIONAL    -- Need OR
}

NS-PmaxList-NB-r13 ::=          SEQUENCE (SIZE (1..maxNS-Pmax-NB-r13)) OF NS-PmaxValue-NB-r13

NS-PmaxValue-NB-r13 ::=         SEQUENCE {
    additionalPmax-r13              P-Max                       OPTIONAL,   -- Need OR
    additionalSpectrumEmission-r13  AdditionalSpectrumEmission
}

ReselectionThreshold-NB-v1360 ::=           INTEGER (32..63)

T-Reselection-NB-r13 ::=        ENUMERATED {s0, s3, s6, s9, s12, s15, s18, s21}

ANR-MeasConfig-NB-r16 ::= SEQUENCE {
    anr-QualityThreshold-r16        NRSRP-Range-NB-r14,
    anr-CarrierList-r16             ANR-CarrierList-NB-r16,
    ...
}

ANR-CarrierList-NB-r16 ::=      SEQUENCE (SIZE (1..maxFreqANR-NB-r16)) OF ANR-Carrier-NB-r16

ANR-Carrier-NB-r16::=           SEQUENCE {
    carrierFreqIndex-r16            INTEGER (1..maxFreq),
    excludedCellList-r16                ANR-ExcludedCellList-NB-r16 OPTIONAL,       -- Need OP
    ...
}

ANR-ExcludedCellList-NB-r16 ::= SEQUENCE (SIZE (1..maxExcludedCell)) OF PhysCellId

ANR-MeasReport-NB-r16 ::=   SEQUENCE {
    servCellIdentity-r16            CellGlobalIdEUTRA           OPTIONAL,
    measResultServCell-r16          MeasResultServCell-NB-r14,
    relativeTimeStamp-r16           INTEGER (0..95),
    measResultList-r16                  SEQUENCE (SIZE (1..maxFreqANR-NB-r16)) OF ANR-MeasResult-NB-r16,
    ...
}

ANR-MeasResult-NB-r16 ::=   SEQUENCE {
    carrierFreq-r16                     CarrierFreq-NB-r13,
    physCellId-r16                      PhysCellId                  OPTIONAL,
    measResultLastServCell-r16          MeasResultServCell-NB-r14,
    measResult-r16                      NRSRP-Range-NB-r14      OPTIONAL,
    cgi-Info-r16                        SEQUENCE {
        cellGlobalId-r16                    CellGlobalIdEUTRA,
        trackingAreaCode-r16                TrackingAreaCode,
        plmn-IdentityList-r16               PLMN-IdentityList2      OPTIONAL
    }   OPTIONAL
}
CQI-NPDCCH-NB-r14 ::=   ENUMERATED {
                            noMeasurements, candidateRep-A, candidateRep-B, candidateRep-C,
                            candidateRep-D, candidateRep-E, candidateRep-F, candidateRep-G,
                            candidateRep-H, candidateRep-I, candidateRep-J, candidateRep-K,
                            candidateRep-L}

CQI-NPDCCH-Short-NB-r14 ::= ENUMERATED {
                                noMeasurements, candidateRep-1, candidateRep-2, candidateRep-3}

MeasResultServCell-NB-r14 ::=   SEQUENCE {
    nrsrpResult-r14                 NRSRP-Range-NB-r14,
    nrsrqResult-r14                 NRSRQ-Range-NB-r14
}

NRSRP-Range-NB-r14 ::=              INTEGER(0..113)

NRSRQ-Range-NB-r14 ::=              INTEGER(-30..46)

NSSS-RRM-Config-NB-r15  ::=             SEQUENCE {
    nsss-RRM-PowerOffset-r15            ENUMERATED {dB-3, db0, dB3},
    nsss-NumOccDiffPrecoders-r15        ENUMERATED {n1, n2, n4, n8} OPTIONAL    --  Need OP
}
EstablishmentCause-NB-r13 ::=           ENUMERATED {
                                            mt-Access, mo-Signalling, mo-Data, mo-ExceptionData,
                                            delayTolerantAccess-v1330, mt-EDT-v1610, spare2, spare1}

UE-Capability-NB-r13 ::=        SEQUENCE {
    accessStratumRelease-r13        AccessStratumRelease-NB-r13,
    ue-Category-NB-r13              ENUMERATED {nb1}                    OPTIONAL,
    multipleDRB-r13                 ENUMERATED {supported}              OPTIONAL,
    pdcp-Parameters-r13             PDCP-Parameters-NB-r13              OPTIONAL,
    phyLayerParameters-r13          PhyLayerParameters-NB-r13,
    rf-Parameters-r13               RF-Parameters-NB-r13,
    dummy                           SEQUENCE {}                         OPTIONAL
}

UE-Capability-NB-Ext-r14-IEs ::=        SEQUENCE {
    ue-Category-NB-r14                  ENUMERATED {nb2}                OPTIONAL,
    mac-Parameters-r14                  MAC-Parameters-NB-r14           OPTIONAL,
    phyLayerParameters-v1430            PhyLayerParameters-NB-v1430     OPTIONAL,
    rf-Parameters-v1430                 RF-Parameters-NB-v1430,
    nonCriticalExtension                UE-Capability-NB-v1440-IEs      OPTIONAL
}

UE-Capability-NB-v1440-IEs ::=      SEQUENCE {
    phyLayerParameters-v1440            PhyLayerParameters-NB-v1440     OPTIONAL,
    nonCriticalExtension                UE-Capability-NB-v14x0-IEs      OPTIONAL
}

UE-Capability-NB-v14x0-IEs ::=      SEQUENCE {
-- Following field is only to be used for late REL-14 extensions
    lateNonCriticalExtension            OCTET STRING                    OPTIONAL,
    nonCriticalExtension                UE-Capability-NB-v1530-IEs      OPTIONAL
}

UE-Capability-NB-v1530-IEs ::=      SEQUENCE {
    earlyData-UP-r15                    ENUMERATED {supported}          OPTIONAL,
    rlc-Parameters-r15                  RLC-Parameters-NB-r15,
    mac-Parameters-v1530                MAC-Parameters-NB-v1530,
    phyLayerParameters-v1530            PhyLayerParameters-NB-v1530     OPTIONAL,
    tdd-UE-Capability-r15               TDD-UE-Capability-NB-r15        OPTIONAL,
    nonCriticalExtension                UE-Capability-NB-v15x0-IEs      OPTIONAL
}

UE-Capability-NB-v15x0-IEs ::=      SEQUENCE {
-- Following field is only to be used for late REL-15 extensions
    lateNonCriticalExtension            OCTET STRING                    OPTIONAL,
    nonCriticalExtension                UE-Capability-NB-v1610-IEs      OPTIONAL
}

UE-Capability-NB-v1610-IEs ::=      SEQUENCE {
    earlySecurityReactivation-r16       ENUMERATED {supported}          OPTIONAL,
    earlyData-UP-5GC-r16                ENUMERATED {supported}          OPTIONAL,
    pur-Parameters-r16                  PUR-Parameters-NB-r16           OPTIONAL,
    mac-Parameters-v1610                MAC-Parameters-NB-v1610,
    phyLayerParameters-v1610            PhyLayerParameters-NB-v1610     OPTIONAL,
    son-Parameters-r16                  SON-Parameters-NB-r16       OPTIONAL,
    measParameters-r16                  MeasParameters-NB-r16,
    tdd-UE-Capability-v1610             TDD-UE-Capability-NB-v1610      OPTIONAL,
    nonCriticalExtension                UE-Capability-NB-v16x0-IEs  OPTIONAL
}

UE-Capability-NB-v16x0-IEs ::=  SEQUENCE {
-- Following field is only to be used for late REL-16 extensions
    lateNonCriticalExtension            OCTET STRING (CONTAINING UE-EUTRA-Capability-v16f0-IEs)                 OPTIONAL,
    nonCriticalExtension                UE-Capability-NB-v1700-IEs      OPTIONAL
}

-- Late non-critical extensions
UE-EUTRA-Capability-v16f0-IEs ::=   SEQUENCE {
    son-Parameters-v16f0                SON-Parameters-NB-v16f0,
    nonCriticalExtension                SEQUENCE    {}                  OPTIONAL
}

-- Regular non-critical extensions
UE-Capability-NB-v1700-IEs ::=  SEQUENCE {
    coverageBasedPaging-r17         ENUMERATED {supported}          OPTIONAL,
    phyLayerParameters-v1700            PhyLayerParameters-NB-v1700,
    ntn-Parameters-r17                  NTN-Parameters-NB-r17               OPTIONAL,
    nonCriticalExtension                UE-Capability-NB-v1710-IEs      OPTIONAL
}

UE-Capability-NB-v1710-IEs ::=  SEQUENCE {
    measParameters-v1710                MeasParameters-NB-v1710     OPTIONAL,
    rf-Parameters-v1710             RF-Parameters-NB-v1710,
    tdd-UE-Capability-v1710         TDD-UE-Capability-NB-v1710,
    nonCriticalExtension                UE-Capability-NB-v1720-IEs  OPTIONAL
}

UE-Capability-NB-v1720-IEs ::=  SEQUENCE {
    ntn-Parameters-v1720                NTN-Parameters-NB-v1720,
    nonCriticalExtension                UE-Capability-NB-v1800-IEs  OPTIONAL
}

UE-Capability-NB-v1800-IEs ::=  SEQUENCE {
    ntn-Parameters-v1800                NTN-Parameters-NB-v1800     OPTIONAL,
    nonCriticalExtension                SEQUENCE {}                 OPTIONAL
}

TDD-UE-Capability-NB-r15 ::=        SEQUENCE {
    ue-Category-NB-r15                  ENUMERATED {nb2}                OPTIONAL,
    phyLayerParametersRel13-r15         PhyLayerParameters-NB-r13       OPTIONAL,
    phyLayerParametersRel14-r15         PhyLayerParameters-NB-v1430     OPTIONAL,
    phyLayerParameters-v1530            PhyLayerParameters-NB-v1530     OPTIONAL,
    ...
}

TDD-UE-Capability-NB-v1610 ::=      SEQUENCE {
    slotSymbolResourceResvDL-r16            ENUMERATED {supported}          OPTIONAL,
    slotSymbolResourceResvUL-r16            ENUMERATED {supported}          OPTIONAL,
    subframeResourceResvDL-r16              ENUMERATED {supported}          OPTIONAL,
    subframeResourceResvUL-r16          ENUMERATED {supported}          OPTIONAL
}

TDD-UE-Capability-NB-v1710 ::=      SEQUENCE {
    phyLayerParameters-v1710                    PhyLayerParameters-NB-v1700     OPTIONAL
}

AccessStratumRelease-NB-r13 ::=     ENUMERATED {rel13, rel14, rel15, rel16, rel17, rel18, spare2, spare1, ...}

PDCP-Parameters-NB-r13      ::= SEQUENCE {
    supportedROHC-Profiles-r13          SEQUENCE {
        profile0x0002                       BOOLEAN,
        profile0x0003                       BOOLEAN,
        profile0x0004                       BOOLEAN,
        profile0x0006                       BOOLEAN,
        profile0x0102                       BOOLEAN,
        profile0x0103                       BOOLEAN,
        profile0x0104                       BOOLEAN
    },
    maxNumberROHC-ContextSessions-r13   ENUMERATED {cs2, cs4, cs8, cs12}    DEFAULT cs2,
    ...
}

RLC-Parameters-NB-r15       ::=     SEQUENCE {
    rlc-UM-r15                          ENUMERATED {supported}              OPTIONAL
}

MAC-Parameters-NB-r14       ::=     SEQUENCE {
    dataInactMon-r14                    ENUMERATED {supported}                  OPTIONAL,
    rai-Support-r14                     ENUMERATED {supported}              OPTIONAL
}

MAC-Parameters-NB-v1530     ::=     SEQUENCE {
    sr-SPS-BSR-r15                      ENUMERATED {supported}          OPTIONAL
}

MAC-Parameters-NB-v1610     ::=     SEQUENCE {
    rai-SupportEnh-r16                  ENUMERATED {supported}          OPTIONAL
}

NTN-Parameters-NB-r17 ::=       SEQUENCE {
    ntn-Connectivity-EPC-r17        ENUMERATED {supported}          OPTIONAL,
    ntn-TA-Report-r17               ENUMERATED {supported}          OPTIONAL,
    ntn-PUR-TimerDelay-r17      ENUMERATED {supported}          OPTIONAL,
    ntn-OffsetTimingEnh-r17     ENUMERATED {supported}          OPTIONAL,
    ntn-ScenarioSupport-r17     ENUMERATED {ngso,gso}               OPTIONAL
}

NTN-Parameters-NB-v1720 ::=     SEQUENCE {
    ntn-SegmentedPrecompensationGaps-r17        ENUMERATED {sym1,sl1,sl2}       OPTIONAL
}

NTN-Parameters-NB-v1800 ::=     SEQUENCE {
    ntn-LocationBasedMeasTrigger-EFC-r18        ENUMERATED {supported}              OPTIONAL,
    ntn-LocationBasedMeasTrigger-EMC-r18        ENUMERATED {supported}              OPTIONAL,
    ntn-TimeBasedMeasTrigger-r18                ENUMERATED {supported}              OPTIONAL,
    ntn-RRC-HarqDisableSingleTB-r18             ENUMERATED {supported}              OPTIONAL,
    ntn-OverriddenHarqDisableSingleTB-r18       ENUMERATED {supported}              OPTIONAL,
    ntn-DCI-HarqDisableSingleTB-r18             ENUMERATED {supported}              OPTIONAL,
    ntn-RRC-HarqDisableMultiTB-r18              ENUMERATED {supported}              OPTIONAL,
    ntn-OverriddenHarqDisableMultiTB-r18        ENUMERATED {supported}              OPTIONAL,
    ntn-DCI-HarqDisableMultiTB-r18              ENUMERATED {supported}              OPTIONAL,
    ntn-UplinkHarq-ModeB-SingleTB-r18           ENUMERATED {supported}              OPTIONAL,
    ntn-UplinkHarq-ModeB-MultiTB-r18            ENUMERATED {supported}              OPTIONAL,
    ntn-HarqEnhScenarioSupport-r18              ENUMERATED {ngso,gso}               OPTIONAL,
    ntn-Triggered-GNSS-Fix-r18                  ENUMERATED {supported}              OPTIONAL,
    ntn-Autonomous-GNSS-Fix-r18                 ENUMERATED {supported}              OPTIONAL,
    ntn-UplinkTxExtension-r18                   ENUMERATED {supported}              OPTIONAL,
    ntn-GNSS-EnhScenarioSupport-r18             ENUMERATED {ngso,gso}               OPTIONAL
}

MeasParameters-NB-r16       ::=     SEQUENCE {
    dl-ChannelQualityReporting-r16      ENUMERATED {supported}          OPTIONAL
}

MeasParameters-NB-v1710 ::=     SEQUENCE {
    connModeMeasIntraFreq-r17           ENUMERATED {supported}          OPTIONAL,
    connModeMeasInterFreq-r17           ENUMERATED {supported}          OPTIONAL
}

PhyLayerParameters-NB-r13   ::=     SEQUENCE {
    multiTone-r13                       ENUMERATED {supported}          OPTIONAL,
    multiCarrier-r13                        ENUMERATED {supported}          OPTIONAL
    }

PhyLayerParameters-NB-v1430 ::=     SEQUENCE {
    multiCarrier-NPRACH-r14             ENUMERATED {supported}          OPTIONAL,
    twoHARQ-Processes-r14               ENUMERATED {supported}          OPTIONAL
}

PhyLayerParameters-NB-v1440 ::=     SEQUENCE {
    interferenceRandomisation-r14       ENUMERATED {supported}          OPTIONAL
}

PhyLayerParameters-NB-v1530 ::=     SEQUENCE {
    mixedOperationMode-r15              ENUMERATED {supported}          OPTIONAL,
    sr-WithHARQ-ACK-r15                 ENUMERATED {supported}          OPTIONAL,
    sr-WithoutHARQ-ACK-r15              ENUMERATED {supported}          OPTIONAL,
    nprach-Format2-r15                  ENUMERATED {supported}          OPTIONAL,
    additionalTransmissionSIB1-r15      ENUMERATED {supported}          OPTIONAL,
    npusch-3dot75kHz-SCS-TDD-r15        ENUMERATED {supported}          OPTIONAL
}

PhyLayerParameters-NB-v1610 ::=     SEQUENCE {
    npdsch-MultiTB-r16                  ENUMERATED {supported}          OPTIONAL,
    npdsch-MultiTB-Interleaving-r16     ENUMERATED {supported}          OPTIONAL,
    npusch-MultiTB-r16                  ENUMERATED {supported}          OPTIONAL,
    npusch-MultiTB-Interleaving-r16     ENUMERATED {supported}          OPTIONAL,
    multiTB-HARQ-AckBundling-r16        ENUMERATED {supported}          OPTIONAL,
    slotSymbolResourceResvDL-r16            ENUMERATED {supported}          OPTIONAL,
    slotSymbolResourceResvUL-r16            ENUMERATED {supported}          OPTIONAL,
    subframeResourceResvDL-r16              ENUMERATED {supported}          OPTIONAL,
    subframeResourceResvUL-r16          ENUMERATED {supported}          OPTIONAL
}

PUR-Parameters-NB-r16   ::=         SEQUENCE {
    pur-CP-EPC-r16                      ENUMERATED {supported}          OPTIONAL,
    pur-CP-5GC-r16                      ENUMERATED {supported}          OPTIONAL,
    pur-UP-EPC-r16                      ENUMERATED {supported}          OPTIONAL,
    pur-UP-5GC-r16                      ENUMERATED {supported}          OPTIONAL,
    pur-NRSRP-Validation-r16            ENUMERATED {supported}          OPTIONAL,
    pur-CP-L1Ack-r16                    ENUMERATED {supported}          OPTIONAL
}

PhyLayerParameters-NB-v1700 ::=     SEQUENCE {
    npdsch-16QAM-r17                    ENUMERATED {supported}          OPTIONAL
}

RF-Parameters-NB-r13    ::=         SEQUENCE {
    supportedBandList-r13               SupportedBandList-NB-r13,
    multiNS-Pmax-r13                    ENUMERATED {supported}      OPTIONAL
}

RF-Parameters-NB-v1430 ::=          SEQUENCE {
    powerClassNB-14dBm-r14              ENUMERATED {supported}      OPTIONAL
}

RF-Parameters-NB-v1710 ::=          SEQUENCE {
    supportedBandList-v1710             SupportedBandList-NB-v1710  OPTIONAL
}

SupportedBandList-NB-r13 ::=        SEQUENCE (SIZE (1..maxBands)) OF SupportedBand-NB-r13

SupportedBandList-NB-v1710 ::=      SEQUENCE (SIZE (1..maxBands)) OF SupportedBand-NB-v1710

SupportedBand-NB-r13    ::=         SEQUENCE {
    band-r13                            FreqBandIndicator-NB-r13,
    powerClassNB-20dBm-r13              ENUMERATED {supported}      OPTIONAL
}

SupportedBand-NB-v1710  ::=     SEQUENCE {
    npusch-16QAM-r17                    ENUMERATED {supported}      OPTIONAL
}

SON-Parameters-NB-r16 ::=           SEQUENCE {
    anr-Report-r16                      ENUMERATED {supported}      OPTIONAL,
    rach-Report-r16                     ENUMERATED {supported}      OPTIONAL
}

SON-Parameters-NB-v16f0 ::=     SEQUENCE {
    locationInfo-r16                    ENUMERATED {supported}              OPTIONAL
}

UE-RadioPagingInfo-NB-r13 ::=       SEQUENCE {
    ue-Category-NB-r13              ENUMERATED {nb1}            OPTIONAL,
    ...,
    [[ multiCarrierPaging-r14       ENUMERATED {true}           OPTIONAL
    ]],
    [[  mixedOperationMode-r15      ENUMERATED {supported}      OPTIONAL,
        wakeUpSignal-r15            ENUMERATED {true}           OPTIONAL,
        wakeUpSignalMinGap-eDRX-r15 ENUMERATED {ms40, ms240, ms1000, ms2000}    OPTIONAL,
        multiCarrierPagingTDD-r15   ENUMERATED {true}           OPTIONAL
    ]],
    [[  ue-Category-NB-r16                  ENUMERATED {nb2}            OPTIONAL,
        groupWakeUpSignal-r16               ENUMERATED {true}           OPTIONAL,
        groupWakeUpSignalAlternation-r16    ENUMERATED {true}           OPTIONAL
    ]]

}

UE-TimersAndConstants-NB-r13 ::=    SEQUENCE {
    t300-r13                            ENUMERATED {
                                            ms2500, ms4000, ms6000, ms10000,
                                            ms15000, ms25000, ms40000, ms60000},
    t301-r13                            ENUMERATED {
                                            ms2500, ms4000, ms6000, ms10000,
                                            ms15000, ms25000, ms40000, ms60000},
    t310-r13                            ENUMERATED {
                                            ms0, ms200, ms500, ms1000, ms2000, ms4000, ms8000},
    n310-r13                            ENUMERATED {
                                            n1, n2, n3, n4, n6, n8, n10, n20},
    t311-r13                            ENUMERATED {
                                            ms1000, ms3000, ms5000, ms10000, ms15000,
                                            ms20000, ms30000},
    n311-r13                            ENUMERATED {
                                            n1, n2, n3, n4, n5, n6, n8, n10},
    ...,
    [[ t311-v1350                       ENUMERATED {
                                            ms40000, ms60000, ms90000, ms120000}
                                                        OPTIONAL    -- Need OR
    ]],
    [[  t300-v1530                      ENUMERATED {
                                            ms80000, ms100000, ms120000}    OPTIONAL,   -- Cond TDD
        t301-v1530                      ENUMERATED {
                                            ms80000, ms100000, ms120000}    OPTIONAL,   -- Cond TDD
        t311-v1530                      ENUMERATED {
                                            ms160000, ms200000}             OPTIONAL,   -- Cond TDD
        t300-r15                        ENUMERATED {ms6000, ms10000, ms15000, ms25000, ms40000,
                                            ms60000, ms80000, ms120000} OPTIONAL        -- Cond EDTorPUR
    ]]
}

SC-MTCH-InfoList-NB-r14 ::=         SEQUENCE (SIZE (0.. maxSC-MTCH-NB-r14)) OF SC-MTCH-Info-NB-r14

SC-MTCH-Info-NB-r14 ::=             SEQUENCE    {
    sc-mtch-CarrierConfig-r14           CHOICE {
        dl-CarrierConfig-r14                    DL-CarrierConfigCommon-NB-r14,
        dl-CarrierIndex-r14                 INTEGER (0.. maxNonAnchorCarriers-NB-r14)
    },
    mbmsSessionInfo-r14                 MBMSSessionInfo-r13,
    g-RNTI-r14                          BIT STRING(SIZE(16)),
    sc-mtch-SchedulingInfo-r14          SC-MTCH-SchedulingInfo-NB-r14       OPTIONAL,   -- Need OP
    sc-mtch-NeighbourCell-r14           BIT STRING (SIZE(maxNeighCell-SCPTM-NB-r14))    OPTIONAL,   -- Need OP
    npdcch-NPDSCH-MaxTBS-SC-MTCH-r14        ENUMERATED {n680, n2536},
    npdcch-NumRepetitions-SC-MTCH-r14   ENUMERATED {r1, r2, r4, r8, r16,
                                                    r32, r64, r128, r256,
                                                    r512, r1024, r2048, spare4,
                                                    spare3, spare2, spare1},
    npdcch-StartSF-SC-MTCH-r14          ENUMERATED {v1dot5, v2, v4, v8,
                                                    v16, v32, v48, v64},
    npdcch-Offset-SC-MTCH-r14           ENUMERATED {zero, oneEighth, oneQuarter,
                                                    threeEighth, oneHalf, fiveEighth,
                                                    threeQuarter, sevenEighth},
    ...
}

SC-MTCH-SchedulingInfo-NB-r14 ::=       SEQUENCE    {
    onDurationTimerSCPTM-r14                ENUMERATED {
                                                pp1, pp2, pp3, pp4,
                                                pp8, pp16, pp32, spare},
    drx-InactivityTimerSCPTM-r14            ENUMERATED {
                                                pp0, pp1, pp2, pp3,
                                                pp4, pp8, pp16, pp32},
    schedulingPeriodStartOffsetSCPTM-r14    CHOICE {
        sf10                                    INTEGER(0..9),
        sf20                                    INTEGER(0..19),
        sf32                                    INTEGER(0..31),
        sf40                                    INTEGER(0..39),
        sf64                                    INTEGER(0..63),
        sf80                                    INTEGER(0..79),
        sf128                                   INTEGER(0..127),
        sf160                                   INTEGER(0..159),
        sf256                                   INTEGER(0..255),
        sf320                                   INTEGER(0..319),
        sf512                                   INTEGER(0..511),
        sf640                                   INTEGER(0..639),
        sf1024                                  INTEGER(0..1023),
        sf2048                                  INTEGER(0..2047),
        sf4096                                  INTEGER(0..4095),
        sf8192                                  INTEGER(0..8191)
    },
    ...
}

SCPTM-NeighbourCellList-NB-r14 ::=  SEQUENCE (SIZE (1..maxNeighCell-SCPTM-NB-r14)) OF PCI-ARFCN-NB-r14

PCI-ARFCN-NB-r14 ::=                SEQUENCE {
    physCellId-r14                      PhysCellId,
    carrierFreq-r14                     CarrierFreq-NB-r13      OPTIONAL    -- Need OP
}

maxFreqANR-NB-r16           INTEGER ::= 2   -- Maximum number of NB-IOT carrier frequencies that can
                                            -- be configured or reported for ANR measurement
maxFreqEUTRA-NB-r16         INTEGER ::= 8   -- Maximum number of EUTRAN carrier frequencies that can
                                            -- be provided as assistance information for inter-RAT
                                            -- cell selection
maxFreqsGERAN-NB-r16        INTEGER ::= 8   -- Maximum number of groups of GERAN carrier frequencies
                                            -- that can be provided as assistance information for
                                            -- inter-RAT cell selection
maxGWUS-Groups-1-NB-r16     INTEGER ::= 15  -- Maximum number of groups for each paging probability
                                            -- group
maxGWUS-Resources-NB-r16    INTEGER ::= 2   -- Maximum number of GWUS resources for each gap
maxGWUS-ProbThresholds-NB-r16 INTEGER ::= 3 -- Maximum number of paging probability thresholds
maxNPRACH-Resources-NB-r13  INTEGER ::= 3   -- Maximum number of NPRACH resources for NB-IoT
maxNonAnchorCarriers-NB-r14 INTEGER ::= 15  -- Maximum number of non-anchor carriers for NB-IoT
maxDRB-NB-r13               INTEGER ::= 2   -- Maximum number of Data Radio Bearers for NB-IoT
maxNeighCell-SCPTM-NB-r14   INTEGER ::= 8   -- Maximum number of SCPTM neighbour cells
maxNS-Pmax-NB-r13           INTEGER ::= 4   -- Maximum number of NS and P-Max values per band
maxSC-MTCH-NB-r14           INTEGER ::= 64  -- Maximum number of SC-MTCHs in one cell for NB-IoT
maxSI-Message-NB-r13        INTEGER ::= 8   -- Maximum number of SI messages for NB-IoT
maxTAC-NB-r17               INTEGER ::= 12  -- Maximum number of Tracking Area Codes
                                            -- broadcast in a cell

END
