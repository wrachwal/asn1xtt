-- ASN1START
-- **************************************************************
--
-- Constant definitions
--
-- **************************************************************

X2AP-Constants {
itu-t (0) identified-organization (4) etsi (0) mobileDomain (0)
eps-Access (21) modules (3) x2ap (2) version1 (1) x2ap-Constants (4) }

DEFINITIONS AUTOMATIC TAGS ::=

BEGIN

IMPORTS
    ProcedureCode,
    ProtocolIE-ID
FROM X2AP-CommonDataTypes;

-- **************************************************************
--
-- Elementary Procedures
--
-- **************************************************************

id-handoverPreparation                                          ProcedureCode ::= 0
id-handoverCancel                                               ProcedureCode ::= 1
id-loadIndication                                               ProcedureCode ::= 2
id-errorIndication                                              ProcedureCode ::= 3
id-snStatusTransfer                                             ProcedureCode ::= 4
id-uEContextRelease                                             ProcedureCode ::= 5
id-x2Setup                                                      ProcedureCode ::= 6
id-reset                                                        ProcedureCode ::= 7
id-eNBConfigurationUpdate                                       ProcedureCode ::= 8
id-resourceStatusReportingInitiation                            ProcedureCode ::= 9
id-resourceStatusReporting                                      ProcedureCode ::= 10
id-privateMessage                                               ProcedureCode ::= 11
id-mobilitySettingsChange                                       ProcedureCode ::= 12
id-rLFIndication                                                ProcedureCode ::= 13
id-handoverReport                                               ProcedureCode ::= 14
id-cellActivation                                               ProcedureCode ::= 15
id-x2Release                                                    ProcedureCode ::= 16
id-x2APMessageTransfer                                          ProcedureCode ::= 17
id-x2Removal                                                    ProcedureCode ::= 18
id-seNBAdditionPreparation                                      ProcedureCode ::= 19
id-seNBReconfigurationCompletion                                ProcedureCode ::= 20
id-meNBinitiatedSeNBModificationPreparation                     ProcedureCode ::= 21
id-seNBinitiatedSeNBModification                                ProcedureCode ::= 22
id-meNBinitiatedSeNBRelease                                     ProcedureCode ::= 23
id-seNBinitiatedSeNBRelease                                     ProcedureCode ::= 24
id-seNBCounterCheck                                             ProcedureCode ::= 25
id-retrieveUEContext                                            ProcedureCode ::= 26
id-sgNBAdditionPreparation                                      ProcedureCode ::= 27
id-sgNBReconfigurationCompletion                                ProcedureCode ::= 28
id-meNBinitiatedSgNBModificationPreparation                     ProcedureCode ::= 29
id-sgNBinitiatedSgNBModification                                ProcedureCode ::= 30
id-meNBinitiatedSgNBRelease                                     ProcedureCode ::= 31
id-sgNBinitiatedSgNBRelease                                     ProcedureCode ::= 32
id-sgNBCounterCheck                                             ProcedureCode ::= 33
id-sgNBChange                                                   ProcedureCode ::= 34
id-rRCTransfer                                                  ProcedureCode ::= 35
id-endcX2Setup                                                  ProcedureCode ::= 36
id-endcConfigurationUpdate                                      ProcedureCode ::= 37
id-secondaryRATDataUsageReport                                  ProcedureCode ::= 38
id-endcCellActivation                                           ProcedureCode ::= 39
id-endcPartialReset                                             ProcedureCode ::= 40
id-eUTRANRCellResourceCoordination                              ProcedureCode ::= 41
id-SgNBActivityNotification                                     ProcedureCode ::= 42
id-endcX2Removal                                                ProcedureCode ::= 43
id-dataForwardingAddressIndication                              ProcedureCode ::= 44
id-gNBStatusIndication                                          ProcedureCode ::= 45
id-deactivateTrace                                              ProcedureCode ::= 46
id-traceStart                                                   ProcedureCode ::= 47
id-endcConfigurationTransfer                                    ProcedureCode ::= 48
id-handoverSuccess                                              ProcedureCode ::= 49
id-conditionalHandoverCancel                                    ProcedureCode ::= 50
id-earlyStatusTransfer                                          ProcedureCode ::= 51
id-cellTrafficTrace                                             ProcedureCode ::= 52
id-endcresourceStatusReporting                                  ProcedureCode ::= 53
id-endcresourceStatusReportingInitiation                        ProcedureCode ::= 54
id-f1CTrafficTransfer                                           ProcedureCode ::= 55
id-UERadioCapabilityIDMapping                                   ProcedureCode ::= 56
id-accessAndMobilityIndication                                  ProcedureCode ::= 57
id-procedure-code-58-not-to-be-used                             ProcedureCode ::= 58
id-CPC-cancel                                                   ProcedureCode ::= 59
id-rachIndication                                               ProcedureCode ::= 60

-- **************************************************************
--
-- Lists
--
-- **************************************************************

maxEARFCN                                   INTEGER ::= 65535
maxEARFCNPlusOne                            INTEGER ::= 65536
newmaxEARFCN                                INTEGER ::= 262143
maxInterfaces                               INTEGER ::= 16
maxCellineNB                                INTEGER ::= 256
maxnoofBands                                INTEGER ::= 16
maxnoofBearers                              INTEGER ::= 256
maxNrOfErrors                               INTEGER ::= 256
maxnoofPDCP-SN                              INTEGER ::= 16
maxnoofEPLMNs                               INTEGER ::= 15
maxnoofEPLMNsPlusOne                        INTEGER ::= 16
maxnoofForbLACs                             INTEGER ::= 4096
maxnoofForbTACs                             INTEGER ::= 4096
maxnoofBPLMNs                               INTEGER ::= 6
maxnoofAdditionalPLMNs                      INTEGER ::= 6
maxnoofNeighbours                           INTEGER ::= 512
maxnoofPRBs                                 INTEGER ::= 110
maxPools                                    INTEGER ::= 16
maxnoofCells                                INTEGER ::= 16
maxnoofMBSFN                                INTEGER ::= 8
maxFailedMeasObjects                        INTEGER ::= 32
maxnoofCellIDforMDT                         INTEGER ::= 32
maxnoofTAforMDT                             INTEGER ::= 8
maxnoofMBMSServiceAreaIdentities            INTEGER ::= 256
maxnoofMDTPLMNs                             INTEGER ::= 16
maxnoofCoMPHypothesisSet                    INTEGER ::= 256
maxnoofCoMPCells                            INTEGER ::= 32
maxUEReport                                 INTEGER ::= 128
maxCellReport                               INTEGER ::= 9
maxnoofPA                                   INTEGER ::= 3
maxCSIProcess                               INTEGER ::= 4
maxCSIReport                                INTEGER ::= 2
maxSubband                                  INTEGER ::= 14
maxofNRNeighbours                           INTEGER ::= 1024
maxCellinengNB                              INTEGER ::= 16384
--  maxnoofNRCarriers                       INTEGER ::= 32
maxnooftimeperiods                          INTEGER ::= 2
maxnoofCellIDforQMC                         INTEGER ::= 32
maxnoofTAforQMC                             INTEGER ::= 8
maxnoofPLMNforQMC                           INTEGER ::= 16
maxUEsinengNBDU                             INTEGER ::= 8192
maxnoofProtectedResourcePatterns            INTEGER ::= 16
maxnoNRcellsSpectrumSharingWithE-UTRA       INTEGER ::= 64
maxnoofNrCellBands                          INTEGER ::= 32
maxnoofBluetoothName                        INTEGER ::= 4
maxnoofWLANName                             INTEGER ::= 4
maxnoofextBPLMNs                            INTEGER ::= 12
maxnoofTLAs                                 INTEGER ::= 16
maxnoofGTPTLAs                              INTEGER ::= 16
maxnoofTNLAssociations                      INTEGER ::= 32
maxnoofCellsinCHO                           INTEGER ::= 8
maxnoofPC5QoSFlows                          INTEGER ::= 2048
maxnoofSSBAreas                             INTEGER ::= 64
maxnoofNRSCSs                               INTEGER ::= 5
maxnoofNRPhysicalResourceBlocks             INTEGER ::= 275
maxnoofNonAnchorCarrierFreqConfig           INTEGER ::= 15
maxnoofRAReports                            INTEGER ::= 64
maxnoofPSCellsPerSN                         INTEGER ::= 8
maxnoofPSCellsPerPrimaryCellinUEHistoryInfo INTEGER ::= 8
maxnoofReportedNRCellsPossiblyAggregated    INTEGER ::= 16
maxnoofPSCellCandidates                     INTEGER ::= 8
maxnoofTargetSgNBs                          INTEGER ::= 8
maxnoofMTCItems                             INTEGER ::= 16
maxnoofCSIRSconfigurations                  INTEGER ::= 96
maxnoofCSIRSneighbourCells                  INTEGER ::= 16
maxnoofCSIRSneighbourCellsInMTC             INTEGER ::= 16
maxnoofSensorName                           INTEGER ::= 3
maxnoofTargetSgNBsMinusOne                  INTEGER ::= 7
maxnoofUEsforRAReportIndications                INTEGER ::= 64



-- **************************************************************
--
-- IEs
--
-- **************************************************************

id-E-RABs-Admitted-Item                                                     ProtocolIE-ID ::= 0
id-E-RABs-Admitted-List                                                     ProtocolIE-ID ::= 1
id-E-RAB-Item                                                               ProtocolIE-ID ::= 2
id-E-RABs-NotAdmitted-List                                                  ProtocolIE-ID ::= 3
id-E-RABs-ToBeSetup-Item                                                    ProtocolIE-ID ::= 4
id-Cause                                                                    ProtocolIE-ID ::= 5
id-CellInformation                                                          ProtocolIE-ID ::= 6
id-CellInformation-Item                                                     ProtocolIE-ID ::= 7
id-New-eNB-UE-X2AP-ID                                                       ProtocolIE-ID ::= 9
id-Old-eNB-UE-X2AP-ID                                                       ProtocolIE-ID ::= 10
id-TargetCell-ID                                                            ProtocolIE-ID ::= 11
id-TargeteNBtoSource-eNBTransparentContainer                                ProtocolIE-ID ::= 12
id-TraceActivation                                                          ProtocolIE-ID ::= 13
id-UE-ContextInformation                                                    ProtocolIE-ID ::= 14
id-UE-HistoryInformation                                                    ProtocolIE-ID ::= 15
id-UE-X2AP-ID                                                               ProtocolIE-ID ::= 16
id-CriticalityDiagnostics                                                   ProtocolIE-ID ::= 17
id-E-RABs-SubjectToStatusTransfer-List                                      ProtocolIE-ID ::= 18
id-E-RABs-SubjectToStatusTransfer-Item                                      ProtocolIE-ID ::= 19
id-ServedCells                                                              ProtocolIE-ID ::= 20
id-GlobalENB-ID                                                             ProtocolIE-ID ::= 21
id-TimeToWait                                                               ProtocolIE-ID ::= 22
id-GUMMEI-ID                                                                ProtocolIE-ID ::= 23
id-GUGroupIDList                                                            ProtocolIE-ID ::= 24
id-ServedCellsToAdd                                                         ProtocolIE-ID ::= 25
id-ServedCellsToModify                                                      ProtocolIE-ID ::= 26
id-ServedCellsToDelete                                                      ProtocolIE-ID ::= 27
id-Registration-Request                                                     ProtocolIE-ID ::= 28
id-CellToReport                                                             ProtocolIE-ID ::= 29
id-ReportingPeriodicity                                                     ProtocolIE-ID ::= 30
id-CellToReport-Item                                                        ProtocolIE-ID ::= 31
id-CellMeasurementResult                                                    ProtocolIE-ID ::= 32
id-CellMeasurementResult-Item                                               ProtocolIE-ID ::= 33
id-GUGroupIDToAddList                                                       ProtocolIE-ID ::= 34
id-GUGroupIDToDeleteList                                                    ProtocolIE-ID ::= 35
id-SRVCCOperationPossible                                                   ProtocolIE-ID ::= 36
id-Measurement-ID                                                           ProtocolIE-ID ::= 37
id-ReportCharacteristics                                                    ProtocolIE-ID ::= 38
id-ENB1-Measurement-ID                                                      ProtocolIE-ID ::= 39
id-ENB2-Measurement-ID                                                      ProtocolIE-ID ::= 40
id-Number-of-Antennaports                                                   ProtocolIE-ID ::= 41
id-CompositeAvailableCapacityGroup                                          ProtocolIE-ID ::= 42
id-ENB1-Cell-ID                                                             ProtocolIE-ID ::= 43
id-ENB2-Cell-ID                                                             ProtocolIE-ID ::= 44
id-ENB2-Proposed-Mobility-Parameters                                        ProtocolIE-ID ::= 45
id-ENB1-Mobility-Parameters                                                 ProtocolIE-ID ::= 46
id-ENB2-Mobility-Parameters-Modification-Range                              ProtocolIE-ID ::= 47
id-FailureCellPCI                                                           ProtocolIE-ID ::= 48
id-Re-establishmentCellECGI                                                 ProtocolIE-ID ::= 49
id-FailureCellCRNTI                                                         ProtocolIE-ID ::= 50
id-ShortMAC-I                                                               ProtocolIE-ID ::= 51
id-SourceCellECGI                                                           ProtocolIE-ID ::= 52
id-FailureCellECGI                                                          ProtocolIE-ID ::= 53
id-HandoverReportType                                                       ProtocolIE-ID ::= 54
id-PRACH-Configuration                                                      ProtocolIE-ID ::= 55
id-MBSFN-Subframe-Info                                                      ProtocolIE-ID ::= 56
id-ServedCellsToActivate                                                    ProtocolIE-ID ::= 57
id-ActivatedCellList                                                        ProtocolIE-ID ::= 58
id-DeactivationIndication                                                   ProtocolIE-ID ::= 59
id-UE-RLF-Report-Container                                                  ProtocolIE-ID ::= 60
id-ABSInformation                                                           ProtocolIE-ID ::= 61
id-InvokeIndication                                                         ProtocolIE-ID ::= 62
id-ABS-Status                                                               ProtocolIE-ID ::= 63
id-PartialSuccessIndicator                                                  ProtocolIE-ID ::= 64
id-MeasurementInitiationResult-List                                         ProtocolIE-ID ::= 65
id-MeasurementInitiationResult-Item                                         ProtocolIE-ID ::= 66
id-MeasurementFailureCause-Item                                             ProtocolIE-ID ::= 67
id-CompleteFailureCauseInformation-List                                     ProtocolIE-ID ::= 68
id-CompleteFailureCauseInformation-Item                                     ProtocolIE-ID ::= 69
id-CSG-Id                                                                   ProtocolIE-ID ::= 70
id-CSGMembershipStatus                                                      ProtocolIE-ID ::= 71
id-MDTConfiguration                                                         ProtocolIE-ID ::= 72
id-ManagementBasedMDTallowed                                                ProtocolIE-ID ::= 74
id-RRCConnSetupIndicator                                                    ProtocolIE-ID ::= 75
id-NeighbourTAC                                                             ProtocolIE-ID ::= 76
id-Time-UE-StayedInCell-EnhancedGranularity                                 ProtocolIE-ID ::= 77
id-RRCConnReestabIndicator                                                  ProtocolIE-ID ::= 78
id-MBMS-Service-Area-List                                                   ProtocolIE-ID ::= 79
id-HO-cause                                                                 ProtocolIE-ID ::= 80
id-TargetCellInUTRAN                                                        ProtocolIE-ID ::= 81
id-MobilityInformation                                                      ProtocolIE-ID ::= 82
id-SourceCellCRNTI                                                          ProtocolIE-ID ::= 83
id-MultibandInfoList                                                        ProtocolIE-ID ::= 84
id-M3Configuration                                                          ProtocolIE-ID ::= 85
id-M4Configuration                                                          ProtocolIE-ID ::= 86
id-M5Configuration                                                          ProtocolIE-ID ::= 87
id-MDT-Location-Info                                                        ProtocolIE-ID ::= 88
id-ManagementBasedMDTPLMNList                                               ProtocolIE-ID ::= 89
id-SignallingBasedMDTPLMNList                                               ProtocolIE-ID ::= 90
id-ReceiveStatusOfULPDCPSDUsExtended                                        ProtocolIE-ID ::= 91
id-ULCOUNTValueExtended                                                     ProtocolIE-ID ::= 92
id-DLCOUNTValueExtended                                                     ProtocolIE-ID ::= 93
id-eARFCNExtension                                                          ProtocolIE-ID ::= 94
id-UL-EARFCNExtension                                                       ProtocolIE-ID ::= 95
id-DL-EARFCNExtension                                                       ProtocolIE-ID ::= 96
id-AdditionalSpecialSubframe-Info                                           ProtocolIE-ID ::= 97
id-Masked-IMEISV                                                            ProtocolIE-ID ::= 98
id-IntendedULDLConfiguration                                                ProtocolIE-ID ::= 99
id-ExtendedULInterferenceOverloadInfo                                       ProtocolIE-ID ::= 100
id-RNL-Header                                                               ProtocolIE-ID ::= 101
id-x2APMessage                                                              ProtocolIE-ID ::= 102
id-ProSeAuthorized                                                          ProtocolIE-ID ::= 103
id-ExpectedUEBehaviour                                                      ProtocolIE-ID ::= 104
id-UE-HistoryInformationFromTheUE                                           ProtocolIE-ID ::= 105
id-DynamicDLTransmissionInformation                                         ProtocolIE-ID ::= 106
id-UE-RLF-Report-Container-for-extended-bands                               ProtocolIE-ID ::= 107
id-CoMPInformation                                                          ProtocolIE-ID ::= 108
id-ReportingPeriodicityRSRPMR                                               ProtocolIE-ID ::= 109
id-RSRPMRList                                                               ProtocolIE-ID ::= 110
id-MeNB-UE-X2AP-ID                                                          ProtocolIE-ID ::= 111
id-SeNB-UE-X2AP-ID                                                          ProtocolIE-ID ::= 112
id-UE-SecurityCapabilities                                                  ProtocolIE-ID ::= 113
id-SeNBSecurityKey                                                          ProtocolIE-ID ::= 114
id-SeNBUEAggregateMaximumBitRate                                            ProtocolIE-ID ::= 115
id-ServingPLMN                                                              ProtocolIE-ID ::= 116
id-E-RABs-ToBeAdded-List                                                    ProtocolIE-ID ::= 117
id-E-RABs-ToBeAdded-Item                                                    ProtocolIE-ID ::= 118
id-MeNBtoSeNBContainer                                                      ProtocolIE-ID ::= 119
id-E-RABs-Admitted-ToBeAdded-List                                           ProtocolIE-ID ::= 120
id-E-RABs-Admitted-ToBeAdded-Item                                           ProtocolIE-ID ::= 121
id-SeNBtoMeNBContainer                                                      ProtocolIE-ID ::= 122
id-ResponseInformationSeNBReconfComp                                        ProtocolIE-ID ::= 123
id-UE-ContextInformationSeNBModReq                                          ProtocolIE-ID ::= 124
id-E-RABs-ToBeAdded-ModReqItem                                              ProtocolIE-ID ::= 125
id-E-RABs-ToBeModified-ModReqItem                                           ProtocolIE-ID ::= 126
id-E-RABs-ToBeReleased-ModReqItem                                           ProtocolIE-ID ::= 127
id-E-RABs-Admitted-ToBeAdded-ModAckList                                     ProtocolIE-ID ::= 128
id-E-RABs-Admitted-ToBeModified-ModAckList                                  ProtocolIE-ID ::= 129
id-E-RABs-Admitted-ToBeReleased-ModAckList                                  ProtocolIE-ID ::= 130
id-E-RABs-Admitted-ToBeAdded-ModAckItem                                     ProtocolIE-ID ::= 131
id-E-RABs-Admitted-ToBeModified-ModAckItem                                  ProtocolIE-ID ::= 132
id-E-RABs-Admitted-ToBeReleased-ModAckItem                                  ProtocolIE-ID ::= 133
id-E-RABs-ToBeReleased-ModReqd                                              ProtocolIE-ID ::= 134
id-E-RABs-ToBeReleased-ModReqdItem                                          ProtocolIE-ID ::= 135
id-SCGChangeIndication                                                      ProtocolIE-ID ::= 136
id-E-RABs-ToBeReleased-List-RelReq                                          ProtocolIE-ID ::= 137
id-E-RABs-ToBeReleased-RelReqItem                                           ProtocolIE-ID ::= 138
id-E-RABs-ToBeReleased-List-RelConf                                         ProtocolIE-ID ::= 139
id-E-RABs-ToBeReleased-RelConfItem                                          ProtocolIE-ID ::= 140
id-E-RABs-SubjectToCounterCheck-List                                        ProtocolIE-ID ::= 141
id-E-RABs-SubjectToCounterCheckItem                                         ProtocolIE-ID ::= 142
id-CoverageModificationList                                                 ProtocolIE-ID ::= 143
id-ReportingPeriodicityCSIR                                                 ProtocolIE-ID ::= 145
id-CSIReportList                                                            ProtocolIE-ID ::= 146
id-UEID                                                                     ProtocolIE-ID ::= 147
id-enhancedRNTP                                                             ProtocolIE-ID ::= 148
id-ProSeUEtoNetworkRelaying                                                 ProtocolIE-ID ::= 149
id-ReceiveStatusOfULPDCPSDUsPDCP-SNlength18                                 ProtocolIE-ID ::= 150
id-ULCOUNTValuePDCP-SNlength18                                              ProtocolIE-ID ::= 151
id-DLCOUNTValuePDCP-SNlength18                                              ProtocolIE-ID ::= 152
id-UE-ContextReferenceAtSeNB                                                ProtocolIE-ID ::= 153
id-UE-ContextKeptIndicator                                                  ProtocolIE-ID ::= 154
id-New-eNB-UE-X2AP-ID-Extension                                             ProtocolIE-ID ::= 155
id-Old-eNB-UE-X2AP-ID-Extension                                             ProtocolIE-ID ::= 156
id-MeNB-UE-X2AP-ID-Extension                                                ProtocolIE-ID ::= 157
id-SeNB-UE-X2AP-ID-Extension                                                ProtocolIE-ID ::= 158
id-LHN-ID                                                                   ProtocolIE-ID ::= 159
id-FreqBandIndicatorPriority                                                ProtocolIE-ID ::= 160
id-M6Configuration                                                          ProtocolIE-ID ::= 161
id-M7Configuration                                                          ProtocolIE-ID ::= 162
id-Tunnel-Information-for-BBF                                               ProtocolIE-ID ::= 163
id-SIPTO-BearerDeactivationIndication                                       ProtocolIE-ID ::= 164
id-GW-TransportLayerAddress                                                 ProtocolIE-ID ::= 165
id-Correlation-ID                                                           ProtocolIE-ID ::= 166
id-SIPTO-Correlation-ID                                                     ProtocolIE-ID ::= 167
id-SIPTO-L-GW-TransportLayerAddress                                         ProtocolIE-ID ::= 168
id-X2RemovalThreshold                                                       ProtocolIE-ID ::= 169
id-CellReportingIndicator                                                   ProtocolIE-ID ::= 170
id-BearerType                                                               ProtocolIE-ID ::= 171
id-resumeID                                                                 ProtocolIE-ID ::= 172
id-UE-ContextInformationRetrieve                                            ProtocolIE-ID ::= 173
id-E-RABs-ToBeSetupRetrieve-Item                                            ProtocolIE-ID ::= 174
id-NewEUTRANCellIdentifier                                                  ProtocolIE-ID ::= 175
id-V2XServicesAuthorized                                                    ProtocolIE-ID ::= 176
id-OffsetOfNbiotChannelNumberToDL-EARFCN                                    ProtocolIE-ID ::= 177
id-OffsetOfNbiotChannelNumberToUL-EARFCN                                    ProtocolIE-ID ::= 178
id-AdditionalSpecialSubframeExtension-Info                                  ProtocolIE-ID ::= 179
id-BandwidthReducedSI                                                       ProtocolIE-ID ::= 180
id-MakeBeforeBreakIndicator                                                 ProtocolIE-ID ::= 181
id-UE-ContextReferenceAtWT                                                  ProtocolIE-ID ::= 182
id-WT-UE-ContextKeptIndicator                                               ProtocolIE-ID ::= 183
id-UESidelinkAggregateMaximumBitRate                                        ProtocolIE-ID ::= 184
id-uL-GTPtunnelEndpoint                                                     ProtocolIE-ID ::= 185
id-DL-scheduling-PDCCH-CCE-usage                                            ProtocolIE-ID ::= 193
id-UL-scheduling-PDCCH-CCE-usage                                            ProtocolIE-ID ::= 194
id-UEAppLayerMeasConfig                                                     ProtocolIE-ID ::= 195
id-extended-e-RAB-MaximumBitrateDL                                          ProtocolIE-ID ::= 196
id-extended-e-RAB-MaximumBitrateUL                                          ProtocolIE-ID ::= 197
id-extended-e-RAB-GuaranteedBitrateDL                                       ProtocolIE-ID ::= 198
id-extended-e-RAB-GuaranteedBitrateUL                                       ProtocolIE-ID ::= 199
id-extended-uEaggregateMaximumBitRateDownlink                               ProtocolIE-ID ::= 200
id-extended-uEaggregateMaximumBitRateUplink                                 ProtocolIE-ID ::= 201
id-NRrestrictioninEPSasSecondaryRAT                                         ProtocolIE-ID ::= 202
id-SgNBSecurityKey                                                          ProtocolIE-ID ::= 203
id-SgNBUEAggregateMaximumBitRate                                            ProtocolIE-ID ::= 204
id-E-RABs-ToBeAdded-SgNBAddReqList                                          ProtocolIE-ID ::= 205
id-MeNBtoSgNBContainer                                                      ProtocolIE-ID ::= 206
id-SgNB-UE-X2AP-ID                                                          ProtocolIE-ID ::= 207
id-RequestedSplitSRBs                                                       ProtocolIE-ID ::= 208
id-E-RABs-ToBeAdded-SgNBAddReq-Item                                         ProtocolIE-ID ::= 209
id-E-RABs-Admitted-ToBeAdded-SgNBAddReqAckList                              ProtocolIE-ID ::= 210
id-SgNBtoMeNBContainer                                                      ProtocolIE-ID ::= 211
id-AdmittedSplitSRBs                                                        ProtocolIE-ID ::= 212
id-E-RABs-Admitted-ToBeAdded-SgNBAddReqAck-Item                             ProtocolIE-ID ::= 213
id-ResponseInformationSgNBReconfComp                                        ProtocolIE-ID ::= 214
id-UE-ContextInformation-SgNBModReq                                         ProtocolIE-ID ::= 215
id-E-RABs-ToBeAdded-SgNBModReq-Item                                         ProtocolIE-ID ::= 216
id-E-RABs-ToBeModified-SgNBModReq-Item                                      ProtocolIE-ID ::= 217
id-E-RABs-ToBeReleased-SgNBModReq-Item                                      ProtocolIE-ID ::= 218
id-E-RABs-Admitted-ToBeAdded-SgNBModAckList                                 ProtocolIE-ID ::= 219
id-E-RABs-Admitted-ToBeModified-SgNBModAckList                              ProtocolIE-ID ::= 220
id-E-RABs-Admitted-ToBeReleased-SgNBModAckList                              ProtocolIE-ID ::= 221
id-E-RABs-Admitted-ToBeAdded-SgNBModAck-Item                                ProtocolIE-ID ::= 222
id-E-RABs-Admitted-ToBeModified-SgNBModAck-Item                             ProtocolIE-ID ::= 223
id-E-RABs-Admitted-ToBeReleased-SgNBModAck-Item                             ProtocolIE-ID ::= 224
id-E-RABs-ToBeReleased-SgNBModReqdList                                      ProtocolIE-ID ::= 225
id-E-RABs-ToBeModified-SgNBModReqdList                                      ProtocolIE-ID ::= 226
id-E-RABs-ToBeReleased-SgNBModReqd-Item                                     ProtocolIE-ID ::= 227
id-E-RABs-ToBeModified-SgNBModReqd-Item                                     ProtocolIE-ID ::= 228
id-E-RABs-ToBeReleased-SgNBChaConfList                                      ProtocolIE-ID ::= 229
id-E-RABs-ToBeReleased-SgNBChaConf-Item                                     ProtocolIE-ID ::= 230
id-E-RABs-ToBeReleased-SgNBRelReqList                                       ProtocolIE-ID ::= 231
id-E-RABs-ToBeReleased-SgNBRelReq-Item                                      ProtocolIE-ID ::= 232
id-E-RABs-ToBeReleased-SgNBRelConfList                                      ProtocolIE-ID ::= 233
id-E-RABs-ToBeReleased-SgNBRelConf-Item                                     ProtocolIE-ID ::= 234
id-E-RABs-SubjectToSgNBCounterCheck-List                                    ProtocolIE-ID ::= 235
id-E-RABs-SubjectToSgNBCounterCheck-Item                                    ProtocolIE-ID ::= 236
id-RRCContainer                                                             ProtocolIE-ID ::= 237
id-SRBType                                                                  ProtocolIE-ID ::= 238
id-Target-SgNB-ID                                                           ProtocolIE-ID ::= 239
id-HandoverRestrictionList                                                  ProtocolIE-ID ::= 240
id-SCGConfigurationQuery                                                    ProtocolIE-ID ::= 241
id-SplitSRB                                                                 ProtocolIE-ID ::= 242
id-NRUeReport                                                               ProtocolIE-ID ::= 243
id-InitiatingNodeType-EndcX2Setup                                           ProtocolIE-ID ::= 244
id-InitiatingNodeType-EndcConfigUpdate                                      ProtocolIE-ID ::= 245
id-RespondingNodeType-EndcX2Setup                                           ProtocolIE-ID ::= 246
id-RespondingNodeType-EndcConfigUpdate                                      ProtocolIE-ID ::= 247
id-NRUESecurityCapabilities                                                 ProtocolIE-ID ::= 248
id-PDCPChangeIndication                                                     ProtocolIE-ID ::= 249
id-ServedEUTRAcellsENDCX2ManagementList                                     ProtocolIE-ID ::= 250
id-CellAssistanceInformation                                                ProtocolIE-ID ::= 251
id-Globalen-gNB-ID                                                          ProtocolIE-ID ::= 252
id-ServedNRcellsENDCX2ManagementList                                        ProtocolIE-ID ::= 253
id-UE-ContextReferenceAtSgNB                                                ProtocolIE-ID ::= 254
id-SecondaryRATUsageReport                                                  ProtocolIE-ID ::= 255
id-ActivationID                                                             ProtocolIE-ID ::= 256
id-MeNBResourceCoordinationInformation                                      ProtocolIE-ID ::= 257
id-SgNBResourceCoordinationInformation                                      ProtocolIE-ID ::= 258
id-ServedEUTRAcellsToModifyListENDCConfUpd                                  ProtocolIE-ID ::= 259
id-ServedEUTRAcellsToDeleteListENDCConfUpd                                  ProtocolIE-ID ::= 260
id-ServedNRcellsToModifyListENDCConfUpd                                     ProtocolIE-ID ::= 261
id-ServedNRcellsToDeleteListENDCConfUpd                                     ProtocolIE-ID ::= 262
id-E-RABUsageReport-Item                                                    ProtocolIE-ID ::= 263
id-Old-SgNB-UE-X2AP-ID                                                      ProtocolIE-ID ::= 264
id-SecondaryRATUsageReportList                                              ProtocolIE-ID ::= 265
id-SecondaryRATUsageReport-Item                                             ProtocolIE-ID ::= 266
id-ServedNRCellsToActivate                                                  ProtocolIE-ID ::= 267
id-ActivatedNRCellList                                                      ProtocolIE-ID ::= 268
id-SelectedPLMN                                                             ProtocolIE-ID ::= 269
id-UEs-ToBeReset                                                            ProtocolIE-ID ::= 270
id-UEs-Admitted-ToBeReset                                                   ProtocolIE-ID ::= 271
id-RRCConfigIndication                                                      ProtocolIE-ID ::= 272
id-DownlinkPacketLossRate                                                   ProtocolIE-ID ::= 273
id-UplinkPacketLossRate                                                     ProtocolIE-ID ::= 274
id-SubscriberProfileIDforRFP                                                ProtocolIE-ID ::= 275
id-serviceType                                                              ProtocolIE-ID ::= 276
id-AerialUEsubscriptionInformation                                          ProtocolIE-ID ::= 277
id-SGNB-Addition-Trigger-Ind                                                ProtocolIE-ID ::= 278
id-MeNBCell-ID                                                              ProtocolIE-ID ::= 279
id-RequestedSplitSRBsrelease                                                ProtocolIE-ID ::= 280
id-AdmittedSplitSRBsrelease                                                 ProtocolIE-ID ::= 281
id-NRS-NSSS-PowerOffset                                                     ProtocolIE-ID ::= 282
id-NSSS-NumOccasionDifferentPrecoder                                        ProtocolIE-ID ::= 283
id-ProtectedEUTRAResourceIndication                                         ProtocolIE-ID ::= 284
id-InitiatingNodeType-EutranrCellResourceCoordination                       ProtocolIE-ID ::= 285
id-RespondingNodeType-EutranrCellResourceCoordination                       ProtocolIE-ID ::= 286
id-DataTrafficResourceIndication                                            ProtocolIE-ID ::= 287
id-SpectrumSharingGroupID                                                   ProtocolIE-ID ::= 288
id-ListofEUTRACellsinEUTRACoordinationReq                                   ProtocolIE-ID ::= 289
id-ListofEUTRACellsinEUTRACoordinationResp                                  ProtocolIE-ID ::= 290
id-ListofEUTRACellsinNRCoordinationReq                                      ProtocolIE-ID ::= 291
id-ListofNRCellsinNRCoordinationReq                                         ProtocolIE-ID ::= 292
id-ListofNRCellsinNRCoordinationResp                                        ProtocolIE-ID ::= 293
id-E-RABs-AdmittedToBeModified-SgNBModConfList                              ProtocolIE-ID ::= 294
id-E-RABs-AdmittedToBeModified-SgNBModConf-Item                             ProtocolIE-ID ::= 295
id-UEContextLevelUserPlaneActivity                                          ProtocolIE-ID ::= 296
id-ERABActivityNotifyItemList                                               ProtocolIE-ID ::= 297
id-InitiatingNodeType-EndcX2Removal                                         ProtocolIE-ID ::= 298
id-RespondingNodeType-EndcX2Removal                                         ProtocolIE-ID ::= 299
id-RLC-Status                                                               ProtocolIE-ID ::= 300
id-CNTypeRestrictions                                                       ProtocolIE-ID ::= 301
id-uLpDCPSnLength                                                           ProtocolIE-ID ::= 302
id-BluetoothMeasurementConfiguration                                        ProtocolIE-ID ::= 303
id-WLANMeasurementConfiguration                                             ProtocolIE-ID ::= 304
id-NRrestrictionin5GS                                                       ProtocolIE-ID ::= 305
id-dL-Forwarding                                                            ProtocolIE-ID ::= 306
id-E-RABs-DataForwardingAddress-List                                        ProtocolIE-ID ::= 307
id-E-RABs-DataForwardingAddress-Item                                        ProtocolIE-ID ::= 308
id-Subscription-Based-UE-DifferentiationInfo                                ProtocolIE-ID ::= 309
id-GNBOverloadInformation                                                   ProtocolIE-ID ::= 310
id-dLPDCPSnLength                                                           ProtocolIE-ID ::= 311
id-secondarysgNBDLGTPTEIDatPDCP                                             ProtocolIE-ID ::= 312
id-secondarymeNBULGTPTEIDatPDCP                                             ProtocolIE-ID ::= 313
id-lCID                                                                     ProtocolIE-ID ::= 314
id-duplicationActivation                                                    ProtocolIE-ID ::= 315
id-ECGI                                                                     ProtocolIE-ID ::= 316
id-RLCMode-transferred                                                      ProtocolIE-ID ::= 317
id-E-RABs-Admitted-ToBeReleased-SgNBRelReqAckList                           ProtocolIE-ID ::= 318
id-E-RABs-Admitted-ToBeReleased-SgNBRelReqAck-Item                          ProtocolIE-ID ::= 319
id-E-RABs-ToBeReleased-SgNBRelReqdList                                      ProtocolIE-ID ::= 320
id-E-RABs-ToBeReleased-SgNBRelReqd-Item                                     ProtocolIE-ID ::= 321
id-NRCGI                                                                    ProtocolIE-ID ::= 322
id-MeNBCoordinationAssistanceInformation                                    ProtocolIE-ID ::= 323
id-SgNBCoordinationAssistanceInformation                                    ProtocolIE-ID ::= 324
id-new-drb-ID-req                                                           ProtocolIE-ID ::= 325
id-endcSONConfigurationTransfer                                             ProtocolIE-ID ::= 326
id-NRNeighbourInfoToAdd                                                     ProtocolIE-ID ::= 327
id-NRNeighbourInfoToModify                                                  ProtocolIE-ID ::= 328
id-DesiredActNotificationLevel                                              ProtocolIE-ID ::= 329
id-LocationInformationSgNBReporting                                         ProtocolIE-ID ::= 330
id-LocationInformationSgNB                                                  ProtocolIE-ID ::= 331
id-LastNG-RANPLMNIdentity                                                   ProtocolIE-ID ::= 332
id-EUTRANTraceID                                                            ProtocolIE-ID ::= 333
id-additionalPLMNs-Item                                                     ProtocolIE-ID ::= 334
id-InterfaceInstanceIndication                                              ProtocolIE-ID ::= 335
id-BPLMN-ID-Info-EUTRA                                                      ProtocolIE-ID ::= 336
id-BPLMN-ID-Info-NR                                                         ProtocolIE-ID ::= 337
id-NBIoT-UL-DL-AlignmentOffset                                              ProtocolIE-ID ::= 338
id-ERABs-transferred-to-MeNB                                                ProtocolIE-ID ::= 339
id-AdditionalRRMPriorityIndex                                               ProtocolIE-ID ::= 340
id-LowerLayerPresenceStatusChange                                           ProtocolIE-ID ::= 341
id-FastMCGRecovery-SN-to-MN                                                 ProtocolIE-ID ::= 342
id-RequestedFastMCGRecoveryViaSRB3                                          ProtocolIE-ID ::= 343
id-AvailableFastMCGRecoveryViaSRB3                                          ProtocolIE-ID ::= 344
id-RequestedFastMCGRecoveryViaSRB3Release                                   ProtocolIE-ID ::= 345
id-ReleaseFastMCGRecoveryViaSRB3                                            ProtocolIE-ID ::= 346
id-FastMCGRecovery-MN-to-SN                                                 ProtocolIE-ID ::= 347
id-PartialListIndicator                                                     ProtocolIE-ID ::= 348
id-MaximumCellListSize                                                      ProtocolIE-ID ::= 349
id-MessageOversizeNotification                                              ProtocolIE-ID ::= 350
id-CellandCapacityAssistInfo                                                ProtocolIE-ID ::= 351
id-TNLConfigurationInfo                                                     ProtocolIE-ID ::= 352
id-TNLA-To-Add-List                                                         ProtocolIE-ID ::= 353
id-TNLA-To-Update-List                                                      ProtocolIE-ID ::= 354
id-TNLA-To-Remove-List                                                      ProtocolIE-ID ::= 355
id-TNLA-Setup-List                                                          ProtocolIE-ID ::= 356
id-TNLA-Failed-To-Setup-List                                                ProtocolIE-ID ::= 357
id-UnlicensedSpectrumRestriction                                                ProtocolIE-ID ::= 358
id-UEContextReferenceatSourceNGRAN                                          ProtocolIE-ID ::= 359
id-EPCHandoverRestrictionListContainer                                      ProtocolIE-ID ::= 360
id-CHOinformation-REQ                                                   ProtocolIE-ID ::= 361
id-CHOinformation-ACK                                                   ProtocolIE-ID ::= 362
id-DAPSRequestInfo                                                          ProtocolIE-ID ::= 363
id-RequestedTargetCellID                                                    ProtocolIE-ID ::= 364
id-CandidateCellsToBeCancelledList                                          ProtocolIE-ID ::= 365
id-DAPSResponseInfo                                                         ProtocolIE-ID ::= 366
id-ProcedureStage                                                           ProtocolIE-ID ::= 367
id-CHO-DC-Indicator                                                         ProtocolIE-ID ::= 368
id-Ethernet-Type                                                            ProtocolIE-ID ::= 369
id-NRV2XServicesAuthorized                                              ProtocolIE-ID ::= 370
id-NRUESidelinkAggregateMaximumBitRate                                      ProtocolIE-ID ::= 371
id-PC5QoSParameters                                                         ProtocolIE-ID ::= 372
id-NPRACHConfiguration                                                      ProtocolIE-ID ::= 373
id-NBIoT-RLF-Report-Container                                               ProtocolIE-ID ::= 374
id-MDTConfigurationNR                                                       ProtocolIE-ID ::= 375
id-PrivacyIndicator                                                         ProtocolIE-ID ::= 376
id-TraceCollectionEntityIPAddress                                           ProtocolIE-ID ::= 377
id-UERadioCapabilityID                                                      ProtocolIE-ID ::= 378
id-SNtriggered                                                              ProtocolIE-ID ::= 379
id-CSI-RSTransmissionIndication                                             ProtocolIE-ID ::= 380
id-DLCarrierList                                                            ProtocolIE-ID ::= 381
id-TargetCellInNGRAN                                                        ProtocolIE-ID ::= 382
id-E-UTRAN-Node1-Measurement-ID                                             ProtocolIE-ID ::= 383
id-E-UTRAN-Node2-Measurement-ID                                             ProtocolIE-ID ::= 384
id-TDDULDLConfigurationCommonNR                                             ProtocolIE-ID ::= 385
id-CarrierList                                                              ProtocolIE-ID ::= 386
id-ULCarrierList                                                            ProtocolIE-ID ::= 387
id-FrequencyShift7p5khz                                                     ProtocolIE-ID ::= 388
id-SSB-PositionsInBurst                                                     ProtocolIE-ID ::= 389
id-NRCellPRACHConfig                                                        ProtocolIE-ID ::= 390
id-CellToReport-NR-ENDC                                                     ProtocolIE-ID ::= 391
id-CellToReport-NR-ENDC-Item                                                ProtocolIE-ID ::= 392
id-CellMeasurementResult-NR-ENDC                                            ProtocolIE-ID ::= 393
id-CellMeasurementResult-NR-ENDC-Item                                       ProtocolIE-ID ::= 394
id-IABNodeIndication                                                        ProtocolIE-ID ::= 395
id-QoS-Mapping-Information                                                  ProtocolIE-ID ::= 396
id-F1CTrafficContainer                                                      ProtocolIE-ID ::= 397
id-IntendedTDD-DL-ULConfiguration-NR                                        ProtocolIE-ID ::= 399
id-UERadioCapability                                                        ProtocolIE-ID ::= 400
id-CellMeasurementResult-E-UTRA-ENDC                                        ProtocolIE-ID ::= 401
id-CellMeasurementResult-E-UTRA-ENDC-Item                                   ProtocolIE-ID ::= 402
id-CellToReport-E-UTRA-ENDC                                                 ProtocolIE-ID ::= 403
id-CellToReport-E-UTRA-ENDC-Item                                            ProtocolIE-ID ::= 404
id-TraceCollectionEntityURI                                                 ProtocolIE-ID ::= 405
id-SFN-Offset                                                               ProtocolIE-ID ::= 406
id-CHO-DC-EarlyDataForwarding                                               ProtocolIE-ID ::= 407
id-IMSvoiceEPSfallbackfrom5G                                                ProtocolIE-ID ::= 408
id-AdditionLocationInformation                                              ProtocolIE-ID ::= 409
id-DirectForwardingPathAvailability                                         ProtocolIE-ID ::= 410
id-sourceNG-RAN-node-id                                                     ProtocolIE-ID ::= 411
id-SourceDLForwardingIPAddress                                              ProtocolIE-ID ::= 412
id-SourceNodeDLForwardingIPAddress                                          ProtocolIE-ID ::= 413
id-NRRAReport                                                   ProtocolIE-ID ::= 414
id-SCG-UE-HistoryInformation                                                ProtocolIE-ID ::= 415
id-PSCellHistoryInformationRetrieve                                         ProtocolIE-ID ::= 416
id-MeasurementResultforNRCellsPossiblyAggregated                            ProtocolIE-ID ::= 417
id-PSCell-UE-HistoryInformation                                             ProtocolIE-ID ::= 418
id-PSCellChangeHistory                                                      ProtocolIE-ID ::= 419
id-CHOinformation-AddReq                                                    ProtocolIE-ID ::= 420
id-CHOinformation-ModReq                                                    ProtocolIE-ID ::= 421
id-SCGActivationStatus                                                      ProtocolIE-ID ::= 422
id-SCGActivationRequest                                                     ProtocolIE-ID ::= 423
id-CPAinformation-REQ                                                       ProtocolIE-ID ::= 424
id-CPAinformation-REQ-ACK                                                   ProtocolIE-ID ::= 425
id-CPAinformation-MOD                                                       ProtocolIE-ID ::= 426
id-CPAinformation-MOD-ACK                                                   ProtocolIE-ID ::= 427
id-CPACinformation-REQD                                                     ProtocolIE-ID ::= 428
id-CPCinformation-REQD                                                      ProtocolIE-ID ::= 429
id-CPCinformation-CONF                                                      ProtocolIE-ID ::= 430
id-CPCinformation-NOTIFY                                                    ProtocolIE-ID ::= 431
id-CPCupdate-MOD                                                            ProtocolIE-ID ::= 432
id-Additional-Measurement-Timing-Configuration-List                         ProtocolIE-ID ::= 433
id-ServedCellSpecificInfoReq-NR                                             ProtocolIE-ID ::= 434
id-SecurityIndication                                                       ProtocolIE-ID ::= 435
id-SecurityResult                                                           ProtocolIE-ID ::= 436
id-RAT-Restrictions                                                         ProtocolIE-ID ::= 437
id-SCGreconfigNotification                                                  ProtocolIE-ID ::= 438
id-MIMOPRBusageInformation                                                  ProtocolIE-ID ::= 439
id-SensorMeasurementConfiguration                                           ProtocolIE-ID ::= 440
id-AdditionalListofForwardingGTPTunnelEndpoint                              ProtocolIE-ID ::= 441
id-M4ReportAmount                                                           ProtocolIE-ID ::= 442
id-M5ReportAmount                                                           ProtocolIE-ID ::= 443
id-M6ReportAmount                                                           ProtocolIE-ID ::= 444
id-M7ReportAmount                                                           ProtocolIE-ID ::= 445
id-CHOTimeBasedInformation                                                  ProtocolIE-ID ::= 446
id-RaReportIndicationList                                                   ProtocolIE-ID ::= 447
id-PSCellListContainer                                                  ProtocolIE-ID ::= 448
id-IABAuthorized                                                            ProtocolIE-ID ::= 449


END
