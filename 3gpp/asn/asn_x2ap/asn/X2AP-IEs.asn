-- ASN1START
-- **************************************************************
--
-- Information Element Definitions
--
-- **************************************************************

X2AP-IEs {
itu-t (0) identified-organization (4) etsi (0) mobileDomain (0)
eps-Access (21) modules (3) x2ap (2) version1 (1) x2ap-IEs (2) }

DEFINITIONS AUTOMATIC TAGS ::=

BEGIN

IMPORTS

    id-E-RAB-Item,
    id-Number-of-Antennaports,
    id-MBSFN-Subframe-Info,
    id-PRACH-Configuration,
    id-CSG-Id,
    id-MDTConfiguration,
    id-SignallingBasedMDTPLMNList,
    id-MultibandInfoList,
    id-FreqBandIndicatorPriority,
    id-NeighbourTAC,
    id-Time-UE-StayedInCell-EnhancedGranularity,
    id-MBMS-Service-Area-List,
    id-HO-cause,
    id-eARFCNExtension,
    id-DL-EARFCNExtension,
    id-UL-EARFCNExtension,
    id-M3Configuration,
    id-M4Configuration,
    id-M5Configuration,
    id-MDT-Location-Info,
    id-NRrestrictioninEPSasSecondaryRAT,
    id-NRrestrictionin5GS,
    id-AdditionalSpecialSubframe-Info,
    id-UEID,
    id-enhancedRNTP,
    id-ProSeUEtoNetworkRelaying,
    id-M6Configuration,
    id-M7Configuration,
    id-OffsetOfNbiotChannelNumberToDL-EARFCN,
    id-OffsetOfNbiotChannelNumberToUL-EARFCN,
    id-AdditionalSpecialSubframeExtension-Info,
    id-BandwidthReducedSI,
    id-extended-e-RAB-MaximumBitrateDL,
    id-extended-e-RAB-MaximumBitrateUL,
    id-extended-e-RAB-GuaranteedBitrateDL,
    id-extended-e-RAB-GuaranteedBitrateUL,
    id-extended-uEaggregateMaximumBitRateDownlink,
    id-extended-uEaggregateMaximumBitRateUplink,
    id-E-RABUsageReport-Item,
    id-SecondaryRATUsageReport-Item,
    id-UEAppLayerMeasConfig,
    id-DL-scheduling-PDCCH-CCE-usage,
    id-UL-scheduling-PDCCH-CCE-usage,
    id-DownlinkPacketLossRate,
    id-UplinkPacketLossRate,
    id-serviceType,
    id-ProtectedEUTRAResourceIndication,
    id-NRS-NSSS-PowerOffset,
    id-NSSS-NumOccasionDifferentPrecoder,
    id-CNTypeRestrictions,
    id-BluetoothMeasurementConfiguration,
    id-WLANMeasurementConfiguration,
    id-ECGI,
    id-NRCGI,
    id-MeNBCoordinationAssistanceInformation,
    id-SgNBCoordinationAssistanceInformation,
    id-NRNeighbourInfoToAdd,
    id-LastNG-RANPLMNIdentity,
    id-BPLMN-ID-Info-EUTRA,
    id-NBIoT-UL-DL-AlignmentOffset,
    id-UnlicensedSpectrumRestriction,
    id-CarrierList,
    id-FrequencyShift7p5khz,
    id-NPRACHConfiguration,
    id-MDTConfigurationNR,
    id-CSI-RSTransmissionIndication,
    id-QoS-Mapping-Information,
    id-IntendedTDD-DL-ULConfiguration-NR,
    id-TraceCollectionEntityURI,
    id-SFN-Offset,
    id-AdditionLocationInformation,
    id-SSB-PositionsInBurst,
    id-NRCellPRACHConfig,
    id-ULCarrierList,
    id-TDDULDLConfigurationCommonNR,
    id-MIMOPRBusageInformation,
    id-Additional-Measurement-Timing-Configuration-List,
    id-ServedCellSpecificInfoReq-NR,
    id-RAT-Restrictions,
    id-PSCellListContainer,
    id-PSCell-UE-HistoryInformation,
    id-SensorMeasurementConfiguration,
    id-M4ReportAmount,
    id-M5ReportAmount,
    id-M6ReportAmount,
    id-M7ReportAmount,
    id-CHOTimeBasedInformation,

    maxnoofBearers,
    maxCellineNB,
    maxEARFCN,
    maxEARFCNPlusOne,
    newmaxEARFCN,
    maxInterfaces,

    maxnoofBands,
    maxnoofBPLMNs,
    maxnoofAdditionalPLMNs,
    maxnoofCells,
    maxnoofEPLMNs,
    maxnoofEPLMNsPlusOne,
    maxnoofForbLACs,
    maxnoofForbTACs,
    maxnoofNeighbours,
    maxnoofPRBs,
    maxNrOfErrors,
    maxPools,
    maxnoofMBSFN,
    maxnoofTAforMDT,
    maxnoofCellIDforMDT,
    maxnoofMBMSServiceAreaIdentities,
    maxnoofMDTPLMNs,
    maxnoofCoMPHypothesisSet,
    maxnoofCoMPCells,
    maxUEReport,
    maxCellReport,
    maxnoofPA,
    maxCSIProcess,
    maxCSIReport,
    maxSubband,
    maxnooftimeperiods,
    maxnoofCellIDforQMC,
    maxnoofTAforQMC,
    maxnoofPLMNforQMC,
    maxUEsinengNBDU,
    maxnoofProtectedResourcePatterns,
    maxnoNRcellsSpectrumSharingWithE-UTRA,
    maxnoofNrCellBands,
    maxnoofBluetoothName,
    maxnoofWLANName,
    maxofNRNeighbours,
    maxnoofextBPLMNs,
    maxnoofTLAs,
    maxnoofGTPTLAs,
    maxnoofTNLAssociations,
    maxnoofCellsinCHO,  maxnoofPC5QoSFlows,
    maxnoofSSBAreas,
    maxnoofNRSCSs,
    maxnoofNRPhysicalResourceBlocks,
    maxnoofNonAnchorCarrierFreqConfig,
    maxnoofRAReports,
    maxnoofPSCellsPerSN,
    maxnoofPSCellsPerPrimaryCellinUEHistoryInfo,
    maxnoofReportedNRCellsPossiblyAggregated,
    maxnoofPSCellCandidates,
    maxnoofTargetSgNBs,
    maxnoofMTCItems,
    maxnoofCSIRSconfigurations,
    maxnoofCSIRSneighbourCells,
    maxnoofCSIRSneighbourCellsInMTC,
    maxCellinengNB,
    maxnoofSensorName,
    maxnoofTargetSgNBsMinusOne,
    maxnoofUEsforRAReportIndications


FROM X2AP-Constants

    Criticality,
    ProcedureCode,
    ProtocolIE-ID,
    TriggeringMessage
FROM X2AP-CommonDataTypes

    ProtocolExtensionContainer{},
    ProtocolIE-Single-Container{},

    X2AP-PROTOCOL-EXTENSION,
    X2AP-PROTOCOL-IES
FROM X2AP-Containers;

-- A

ABSInformation ::= CHOICE {
    fdd                 ABSInformationFDD,
    tdd                 ABSInformationTDD,
    abs-inactive        NULL,
    ...
}

ABSInformationFDD ::= SEQUENCE {
    abs-pattern-info                    BIT STRING (SIZE(40)),
    numberOfCellSpecificAntennaPorts    ENUMERATED {one, two, four, ...},
    measurement-subset                  BIT STRING (SIZE(40)),
    iE-Extensions                       ProtocolExtensionContainer { {ABSInformationFDD-ExtIEs} } OPTIONAL,
    ...
}

ABSInformationFDD-ExtIEs X2AP-PROTOCOL-EXTENSION ::= {
    ...
}

ABSInformationTDD ::= SEQUENCE {
    abs-pattern-info                    BIT STRING (SIZE(1..70, ...)),
    numberOfCellSpecificAntennaPorts    ENUMERATED {one, two, four, ...},
    measurement-subset                  BIT STRING (SIZE(1..70, ...)),
    iE-Extensions                       ProtocolExtensionContainer { {ABSInformationTDD-ExtIEs} } OPTIONAL,
    ...
}

ABSInformationTDD-ExtIEs X2AP-PROTOCOL-EXTENSION ::= {
    ...
}

ABS-Status ::= SEQUENCE {
    dL-ABS-status                               DL-ABS-status,
    usableABSInformation                        UsableABSInformation,
    iE-Extensions                               ProtocolExtensionContainer { {ABS-Status-ExtIEs} } OPTIONAL,
    ...
}

ABS-Status-ExtIEs X2AP-PROTOCOL-EXTENSION ::= {
    ...
}

ActivationID ::= INTEGER (0..255)

Additional-Measurement-Timing-Configuration-List ::= SEQUENCE (SIZE(1.. maxnoofMTCItems)) OF Additional-Measurement-Timing-Configuration-Item

Additional-Measurement-Timing-Configuration-Item ::= SEQUENCE {
    additionalMeasurementTimingConfiguration        INTEGER(0..16),
    csi-RS-MTC-Configuration-List       CSI-RS-MTC-Configuration-List,
    iE-Extensions                       ProtocolExtensionContainer { { Additional-Measurement-Timing-Configuration-Item-ExtIEs} }   OPTIONAL,
    ...
}

Additional-Measurement-Timing-Configuration-Item-ExtIEs X2AP-PROTOCOL-EXTENSION ::= {
    ...
}

CSI-RS-MTC-Configuration-List ::= SEQUENCE (SIZE(1.. maxnoofCSIRSconfigurations)) OF CSI-RS-MTC-Configuration-Item

CSI-RS-MTC-Configuration-Item ::= SEQUENCE {
    csi-RS-Index            INTEGER(0..95),
    csi-RS-Status           ENUMERATED {activated,deactivated, ...},
    csi-RS-Neighbour-List   CSI-RS-Neighbour-List OPTIONAL,
    iE-Extensions           ProtocolExtensionContainer { { CSI-RS-MTC-Configuration-Item-ExtIEs} }  OPTIONAL,
    ...
}

CSI-RS-MTC-Configuration-Item-ExtIEs X2AP-PROTOCOL-EXTENSION ::= {
    ...
}

CSI-RS-Neighbour-List ::= SEQUENCE (SIZE(1.. maxnoofCSIRSneighbourCells)) OF CSI-RS-Neighbour-Item

CSI-RS-Neighbour-Item ::= SEQUENCE {
    nr-cgi                          NRCGI,
    csi-RS-MTC-Neighbour-List   CSI-RS-MTC-Neighbour-List OPTIONAL,
    iE-Extensions           ProtocolExtensionContainer { { CSI-RS-Neighbour-Item-ExtIEs} }  OPTIONAL,
    ...
}

CSI-RS-Neighbour-Item-ExtIEs X2AP-PROTOCOL-EXTENSION ::= {
    ...
}


CSI-RS-MTC-Neighbour-List ::= SEQUENCE (SIZE(1.. maxnoofCSIRSneighbourCellsInMTC)) OF CSI-RS-MTC-Neighbour-Item

CSI-RS-MTC-Neighbour-Item ::= SEQUENCE {
    csi-RS-Index        INTEGER(0..95),
    iE-Extensions       ProtocolExtensionContainer { { CSI-RS-MTC-Neighbour-Item-ExtIEs} }  OPTIONAL,
    ...
}


CSI-RS-MTC-Neighbour-Item-ExtIEs X2AP-PROTOCOL-EXTENSION ::= {
    ...
}

AdditionalListofForwardingGTPTunnelEndpoint ::= SEQUENCE (SIZE(1..maxnoofTargetSgNBsMinusOne)) OF AdditionalListofForwardingGTPTunnelEndpoint-Item

AdditionalListofForwardingGTPTunnelEndpoint-Item ::= SEQUENCE {
    uL-GTPtunnelEndpoint            GTPtunnelEndpoint                                                   OPTIONAL,
    dL-GTPtunnelEndpoint            GTPtunnelEndpoint                                                   OPTIONAL,
    iE-Extensions       ProtocolExtensionContainer { { AdditionalListofForwardingGTPTunnelEndpoint-Item-ExtIEs} } OPTIONAL,
    ...
}

AdditionalListofForwardingGTPTunnelEndpoint-Item-ExtIEs X2AP-PROTOCOL-EXTENSION ::= {
    ...
}

AdditionLocationInformation ::= ENUMERATED {
    includePSCell,
    ...
}

AdditionalRRMPriorityIndex ::= BIT STRING (SIZE(32))

AdditionalSpecialSubframe-Info ::=      SEQUENCE {
    additionalspecialSubframePatterns       AdditionalSpecialSubframePatterns,
    cyclicPrefixDL                          CyclicPrefixDL,
    cyclicPrefixUL                          CyclicPrefixUL,
    iE-Extensions                           ProtocolExtensionContainer { {AdditionalSpecialSubframe-Info-ExtIEs} } OPTIONAL,
    ...
}

AdditionalSpecialSubframe-Info-ExtIEs X2AP-PROTOCOL-EXTENSION ::= {
    ...
}

AdditionalSpecialSubframePatterns ::= ENUMERATED {
    ssp0,
    ssp1,
    ssp2,
    ssp3,
    ssp4,
    ssp5,
    ssp6,
    ssp7,
    ssp8,
    ssp9,
    ...
}

AdditionalSpecialSubframeExtension-Info ::=     SEQUENCE {
    additionalspecialSubframePatternsExtension  AdditionalSpecialSubframePatternsExtension,
    cyclicPrefixDL                              CyclicPrefixDL,
    cyclicPrefixUL                              CyclicPrefixUL,
    iE-Extensions                               ProtocolExtensionContainer { {AdditionalSpecialSubframeExtension-Info-ExtIEs} } OPTIONAL,
    ...
}

AdditionalSpecialSubframeExtension-Info-ExtIEs X2AP-PROTOCOL-EXTENSION ::= {
    ...
}

AdditionalSpecialSubframePatternsExtension ::= ENUMERATED {
    ssp10,
    ...
}

AvailableFastMCGRecoveryViaSRB3 ::= ENUMERATED {true,...}

AerialUEsubscriptionInformation ::= ENUMERATED {
    allowed,
    not-allowed,
    ...
}

AllocationAndRetentionPriority ::= SEQUENCE {
    priorityLevel               PriorityLevel,
    pre-emptionCapability       Pre-emptionCapability,
    pre-emptionVulnerability    Pre-emptionVulnerability,
    iE-Extensions               ProtocolExtensionContainer { {AllocationAndRetentionPriority-ExtIEs} } OPTIONAL,
    ...
}

AllocationAndRetentionPriority-ExtIEs X2AP-PROTOCOL-EXTENSION ::= {
    ...
}

AreaScopeOfMDT ::= CHOICE {
    cellBased                   CellBasedMDT,
    tABased                     TABasedMDT,
    pLMNWide                    NULL,
    ...,
    tAIBased                    TAIBasedMDT
}

AreaScopeOfQMC ::= CHOICE {
    cellBased                   CellBasedQMC,
    tABased                     TABasedQMC,
    tAIBased                    TAIBasedQMC,
    pLMNAreaBased               PLMNAreaBasedQMC,
    ...
}

AS-SecurityInformation ::= SEQUENCE {
    key-eNodeB-star     Key-eNodeB-Star,
    nextHopChainingCount            NextHopChainingCount,
    iE-Extensions                       ProtocolExtensionContainer { {AS-SecurityInformation-ExtIEs} } OPTIONAL,
    ...
}

AS-SecurityInformation-ExtIEs X2AP-PROTOCOL-EXTENSION ::= {
    ...
}

AdditionalPLMNs-Item ::= SEQUENCE (SIZE(1..maxnoofAdditionalPLMNs)) OF PLMN-Identity


-- B

BandwidthReducedSI::= ENUMERATED {
    scheduled,
    ...
}

BearerType ::= ENUMERATED {
    non-IP,
    ...
}

BenefitMetric ::= INTEGER (-101..100, ...)

BitRate ::= INTEGER (0..10000000000)
BroadcastPLMNs-Item ::= SEQUENCE (SIZE(1..maxnoofBPLMNs)) OF PLMN-Identity

BluetoothMeasurementConfiguration ::= SEQUENCE {
    bluetoothMeasConfig             BluetoothMeasConfig,
    bluetoothMeasConfigNameList     BluetoothMeasConfigNameList         OPTIONAL,
    bt-rssi                         ENUMERATED {true, ...}              OPTIONAL,
    iE-Extensions       ProtocolExtensionContainer { {BluetoothMeasurementConfiguration-ExtIEs} } OPTIONAL,
    ...
}

BluetoothMeasurementConfiguration-ExtIEs X2AP-PROTOCOL-EXTENSION ::= {
    ...
}

BluetoothMeasConfigNameList ::= SEQUENCE (SIZE(1..maxnoofBluetoothName)) OF BluetoothName

BluetoothMeasConfig::= ENUMERATED {setup,...}

BluetoothName ::= OCTET STRING (SIZE (1..248))

BPLMN-ID-Info-EUTRA ::= SEQUENCE (SIZE(1..maxnoofBPLMNs)) OF BPLMN-ID-Info-EUTRA-Item

BPLMN-ID-Info-EUTRA-Item ::= SEQUENCE {
    broadcastPLMNs                  BroadcastPLMNs-Item,
    tac                             TAC,
    e-utraCI                        EUTRANCellIdentifier,
    iE-Extension                    ProtocolExtensionContainer { {BPLMN-ID-Info-EUTRA-Item-ExtIEs} } OPTIONAL,
    ...
}

BPLMN-ID-Info-EUTRA-Item-ExtIEs X2AP-PROTOCOL-EXTENSION ::= {
    ...
}

BPLMN-ID-Info-NR ::= SEQUENCE (SIZE(1..maxnoofextBPLMNs)) OF BPLMN-ID-Info-NR-Item

BPLMN-ID-Info-NR-Item ::= SEQUENCE {
    broadcastPLMNs                  BroadcastextPLMNs,
    fiveGS-TAC                      FiveGS-TAC      OPTIONAL,
    nr-CI                           NRCellIdentifier,
    iE-Extension                    ProtocolExtensionContainer { {BPLMN-ID-Info-NR-Item-ExtIEs} } OPTIONAL,
    ...
}

BPLMN-ID-Info-NR-Item-ExtIEs X2AP-PROTOCOL-EXTENSION ::= {
    ...
}

BroadcastextPLMNs ::= SEQUENCE (SIZE(1..maxnoofextBPLMNs)) OF PLMN-Identity

-- C

CapacityValue ::= INTEGER (0..100)

Cause ::= CHOICE {
    radioNetwork        CauseRadioNetwork,
    transport           CauseTransport,
    protocol            CauseProtocol,
    misc                CauseMisc,
    ...
}

CauseMisc ::= ENUMERATED {
    control-processing-overload,
    hardware-failure,
    om-intervention,
    not-enough-user-plane-processing-resources,
    unspecified,
    ...
}

CauseProtocol ::= ENUMERATED {
    transfer-syntax-error,
    abstract-syntax-error-reject,
    abstract-syntax-error-ignore-and-notify,
    message-not-compatible-with-receiver-state,
    semantic-error,
    unspecified,
    abstract-syntax-error-falsely-constructed-message,
    ...
}

CauseRadioNetwork ::= ENUMERATED {
    handover-desirable-for-radio-reasons,
    time-critical-handover,
    resource-optimisation-handover,
    reduce-load-in-serving-cell,
    partial-handover,
    unknown-new-eNB-UE-X2AP-ID,
    unknown-old-eNB-UE-X2AP-ID,
    unknown-pair-of-UE-X2AP-ID,
    ho-target-not-allowed,
    tx2relocoverall-expiry,
    trelocprep-expiry,
    cell-not-available,
    no-radio-resources-available-in-target-cell,
    invalid-MME-GroupID,
    unknown-MME-Code,
    encryption-and-or-integrity-protection-algorithms-not-supported,
    reportCharacteristicsEmpty,
    noReportPeriodicity,
    existingMeasurementID,
    unknown-eNB-Measurement-ID,
    measurement-temporarily-not-available,
    unspecified,
    ...,
    load-balancing,
    handover-optimisation,
    value-out-of-allowed-range,
    multiple-E-RAB-ID-instances,
    switch-off-ongoing,
    not-supported-QCI-value,
    measurement-not-supported-for-the-object,
    tDCoverall-expiry,
    tDCprep-expiry,
    action-desirable-for-radio-reasons,
    reduce-load,
    resource-optimisation,
    time-critical-action,
    target-not-allowed,
    no-radio-resources-available,
    invalid-QoS-combination,
    encryption-algorithms-not-supported,
    procedure-cancelled,
    rRM-purpose,
    improve-user-bit-rate,
    user-inactivity,
    radio-connection-with-UE-lost,
    failure-in-the-radio-interface-procedure,
    bearer-option-not-supported,
    mCG-Mobility,
    sCG-Mobility,
    count-reaches-max-value,
    unknown-old-en-gNB-UE-X2AP-ID,
    pDCP-Overload,
    cho-cpc-resources-tobechanged,
    ue-power-saving,
    insufficient-ue-capabilities,
    normal-release,
    unknown-E-UTRAN-Node-Measurement-ID,
    sCG-activation-deactivation-failure,
    sCG-deactivation-failure-due-to-data-transmission,
    up-integrity-protection-not-possible


}

CauseTransport ::= ENUMERATED {
    transport-resource-unavailable,
    unspecified,
    ...
}

CellBasedMDT::= SEQUENCE {
    cellIdListforMDT    CellIdListforMDT,
    iE-Extensions       ProtocolExtensionContainer { {CellBasedMDT-ExtIEs} } OPTIONAL,
    ...
}

CellBasedMDT-ExtIEs X2AP-PROTOCOL-EXTENSION ::= {
    ...
}

CellBasedQMC::= SEQUENCE {
    cellIdListforQMC        CellIdListforQMC,
    iE-Extensions       ProtocolExtensionContainer { {CellBasedQMC-ExtIEs} } OPTIONAL,
    ...
}

CellBasedQMC-ExtIEs X2AP-PROTOCOL-EXTENSION ::= {
    ...
}

CellCapacityClassValue ::= INTEGER (1..100, ...)

CellDeploymentStatusIndicator ::= ENUMERATED {pre-change-notification, ...}

CellIdListforMDT ::= SEQUENCE (SIZE(1..maxnoofCellIDforMDT)) OF ECGI

CellIdListforQMC ::= SEQUENCE (SIZE(1..maxnoofCellIDforQMC)) OF ECGI

CellReplacingInfo ::= SEQUENCE {
    replacingCellsList              ReplacingCellsList,
    iE-Extensions                   ProtocolExtensionContainer { {CellReplacingInfo-ExtIEs}}    OPTIONAL,
    ...
}

CellReplacingInfo-ExtIEs X2AP-PROTOCOL-EXTENSION ::= {
    ...
}

CellReportingIndicator ::= ENUMERATED {stop-request, ... }

Cell-Size ::= ENUMERATED {verysmall, small, medium, large, ... }


CellType ::= SEQUENCE {
    cell-Size                       Cell-Size,
    iE-Extensions                   ProtocolExtensionContainer { {CellType-ExtIEs}} OPTIONAL,
    ...
}

CellType-ExtIEs X2AP-PROTOCOL-EXTENSION ::= {
    ...
}


CPACcandidatePSCells-list ::= SEQUENCE (SIZE(1..maxnoofPSCellCandidates)) OF CPACcandidatePSCells-item

CPACcandidatePSCells-item ::= SEQUENCE {
    pscell-id                       NRCGI,
    iE-Extensions                   ProtocolExtensionContainer { {CPACcandidatePSCells-item-ExtIEs}}    OPTIONAL,
    ...
}

CPACcandidatePSCells-item-ExtIEs X2AP-PROTOCOL-EXTENSION ::= {
    ...
}


CPCindicator ::= ENUMERATED {cpc-initiation, cpc-modification, cpc-cancel, ...}


CPCdataforwarding ::= ENUMERATED {cpc-triggered, early-data-transmission-stop, ..., coordination-only}


CPAinformation-REQ ::= SEQUENCE {
    max-no-of-pscells               INTEGER (1..maxnoofPSCellCandidates),
    estimatedArrivalProbability     CHO-Probability                         OPTIONAL,
    iE-Extensions       ProtocolExtensionContainer { {CPAinformation-REQ-ExtIEs} } OPTIONAL,
    ...
}

CPAinformation-REQ-ExtIEs X2AP-PROTOCOL-EXTENSION ::= {
    ...
}


CPAinformation-REQ-ACK ::= SEQUENCE {
    candidate-pscells                   CPACcandidatePSCells-list,
    iE-Extensions       ProtocolExtensionContainer { {CPAinformation-REQ-ACK-ExtIEs} } OPTIONAL,
    ...
}

CPAinformation-REQ-ACK-ExtIEs X2AP-PROTOCOL-EXTENSION ::= {
    ...
}


CPCinformation-REQD ::= SEQUENCE {
    cpc-target-sgnb-list        CPC-target-SgNB-reqd-list,
    iE-Extensions           ProtocolExtensionContainer { {CPCinformation-REQD-ExtIEs} } OPTIONAL,
    ...
}


CPCinformation-REQD-ExtIEs X2AP-PROTOCOL-EXTENSION ::= {
    ...
}


CPC-target-SgNB-reqd-list ::= SEQUENCE (SIZE(1..maxnoofTargetSgNBs)) OF CPC-target-SgNB-reqd-item


CPC-target-SgNB-reqd-item ::= SEQUENCE {
    target-SgNB-ID                  GlobalGNB-ID,
    cpc-indicator                   CPCindicator,
    max-no-of-pscells               INTEGER (1..maxnoofPSCellCandidates),
    estimatedArrivalProbability     CHO-Probability                         OPTIONAL,
    sgNBtoMeNBContainer             SgNBtoMeNBContainer,
    iE-Extensions       ProtocolExtensionContainer { {CPC-target-SgNB-reqd-item-ExtIEs} } OPTIONAL,
    ...
}

CPC-target-SgNB-reqd-item-ExtIEs X2AP-PROTOCOL-EXTENSION ::= {
    ...
}


CPCinformation-CONF ::= SEQUENCE {
    cpc-target-sgnb-list        CPC-target-SgNB-conf-list,
    iE-Extensions           ProtocolExtensionContainer { {CPCinformation-CONF-ExtIEs} } OPTIONAL,
    ...
}


CPCinformation-CONF-ExtIEs X2AP-PROTOCOL-EXTENSION ::= {
    ...
}


CPC-target-SgNB-conf-list ::= SEQUENCE (SIZE(1..maxnoofTargetSgNBs)) OF CPC-target-SgNB-conf-item


CPC-target-SgNB-conf-item ::= SEQUENCE {
    target-SgNB-ID                      GlobalGNB-ID,
    candidate-pscells                   CPACcandidatePSCells-list,
    iE-Extensions       ProtocolExtensionContainer { {CPC-target-SgNB-conf-item-ExtIEs} } OPTIONAL,
    ...
}

CPC-target-SgNB-conf-item-ExtIEs X2AP-PROTOCOL-EXTENSION ::= {
    ...
}


CPCinformation-NOTIFY ::= SEQUENCE {
    cpc-indicator                   CPCdataforwarding,
    iE-Extensions       ProtocolExtensionContainer { {CPCinformation-NOTIFY-ExtIEs} } OPTIONAL,
    ...
}

CPCinformation-NOTIFY-ExtIEs X2AP-PROTOCOL-EXTENSION ::= {
    ...
}


CPAinformation-MOD ::= SEQUENCE {
    max-no-of-pscells               INTEGER (1..maxnoofPSCellCandidates)    OPTIONAL,
    estimatedArrivalProbability     CHO-Probability                         OPTIONAL,
    iE-Extensions       ProtocolExtensionContainer { {CPAinformation-MOD-ExtIEs} } OPTIONAL,
    ...
}

CPAinformation-MOD-ExtIEs X2AP-PROTOCOL-EXTENSION ::= {
    ...
}


CPCupdate-MOD ::= SEQUENCE {

    cpc-target-sgnb-list                    CPC-target-SgNB-mod-list,
    iE-Extensions                       ProtocolExtensionContainer { {CPCupdate-MOD-ExtIEs} } OPTIONAL,
    ...
}

CPCupdate-MOD-ExtIEs X2AP-PROTOCOL-EXTENSION ::= {
    ...
}

CPC-target-SgNB-mod-list ::= SEQUENCE (SIZE(1..maxnoofTargetSgNBs)) OF CPC-target-SgNB-mod-item

CPC-target-SgNB-mod-item ::= SEQUENCE {
    target-SgNB-ID                      GlobalGNB-ID,
    candidate-pscells                   CPACcandidatePSCells-list,
    iE-Extensions       ProtocolExtensionContainer { {CPC-target-SgNB-mod-item-ExtIEs} } OPTIONAL,
    ...
}

CPC-target-SgNB-mod-item-ExtIEs X2AP-PROTOCOL-EXTENSION ::= {
    ...
}


CPAinformation-MOD-ACK ::= SEQUENCE {
    candidate-pscells                   CPACcandidatePSCells-list,
    iE-Extensions                       ProtocolExtensionContainer { {CPAinformation-MOD-ACK-ExtIEs} } OPTIONAL,
    ...
}

CPAinformation-MOD-ACK-ExtIEs X2AP-PROTOCOL-EXTENSION ::= {
    ...
}


CPACinformation-REQD ::= SEQUENCE {
    candidate-pscells                   CPACcandidatePSCells-list,
    iE-Extensions                       ProtocolExtensionContainer { { CPACinformation-REQD-ExtIEs} } OPTIONAL,
    ...
}

CPACinformation-REQD-ExtIEs X2AP-PROTOCOL-EXTENSION ::= {
    ...
}


CHO-DC-EarlyDataForwarding ::= ENUMERATED {stop, ...}

CHO-DC-Indicator ::= ENUMERATED {true, ..., coordination-only}

CNTypeRestrictions ::= SEQUENCE (SIZE(1.. maxnoofEPLMNsPlusOne)) OF CNTypeRestrictionsItem

CNTypeRestrictionsItem ::= SEQUENCE {
    plmn-Id             PLMN-Identity,
    cn-type             ENUMERATED {fiveGC-forbidden, ... , epc-forbidden},
    iE-Extensions       ProtocolExtensionContainer { {CNTypeRestrictionsItem-ExtIEs} } OPTIONAL,
    ...
}

CNTypeRestrictionsItem-ExtIEs X2AP-PROTOCOL-EXTENSION ::= {
    ...
}

CoMPHypothesisSet ::= SEQUENCE (SIZE(1..maxnoofCoMPCells)) OF CoMPHypothesisSetItem

CoMPHypothesisSetItem ::= SEQUENCE {
    coMPCellID                      ECGI,
    coMPHypothesis                  BIT STRING (SIZE(6..4400, ...)),
    iE-Extensions                   ProtocolExtensionContainer { {CoMPHypothesisSetItem-ExtIEs} } OPTIONAL,
    ...
}

CoMPHypothesisSetItem-ExtIEs X2AP-PROTOCOL-EXTENSION ::= {
    ...
}

CoMPInformation ::= SEQUENCE {
    coMPInformationItem                     CoMPInformationItem,
    coMPInformationStartTime                CoMPInformationStartTime,
    iE-Extensions                           ProtocolExtensionContainer { {CoMPInformation-ExtIEs} } OPTIONAL,
    ...
}

CoMPInformation-ExtIEs X2AP-PROTOCOL-EXTENSION ::= {
    ...
}

CoMPInformationItem ::= SEQUENCE (SIZE(1..maxnoofCoMPHypothesisSet)) OF
    SEQUENCE {
        coMPHypothesisSet                   CoMPHypothesisSet,
        benefitMetric                       BenefitMetric,
        iE-Extensions                       ProtocolExtensionContainer { {CoMPInformationItem-ExtIEs} } OPTIONAL,
        ...
    }

CoMPInformationItem-ExtIEs X2AP-PROTOCOL-EXTENSION ::= {
    ...
}

CoMPInformationStartTime ::= SEQUENCE (SIZE(0..1)) OF
    SEQUENCE {
        startSFN                            INTEGER (0..1023, ...),
        startSubframeNumber                 INTEGER (0..9, ...),
        iE-Extensions                       ProtocolExtensionContainer { {CoMPInformationStartTime-ExtIEs} } OPTIONAL,
        ...
    }

CoMPInformationStartTime-ExtIEs X2AP-PROTOCOL-EXTENSION ::= {
    ...
}

CompositeAvailableCapacity ::= SEQUENCE {
    cellCapacityClassValue                          CellCapacityClassValue              OPTIONAL,
    capacityValue                                   CapacityValue,
    iE-Extensions                                   ProtocolExtensionContainer { {CompositeAvailableCapacity-ExtIEs} } OPTIONAL,
    ...
}

CompositeAvailableCapacity-ExtIEs X2AP-PROTOCOL-EXTENSION ::= {
    ...
}

CompositeAvailableCapacityGroup ::= SEQUENCE {
    dL-CompositeAvailableCapacity                   CompositeAvailableCapacity,
    uL-CompositeAvailableCapacity                   CompositeAvailableCapacity,
    iE-Extensions                                   ProtocolExtensionContainer { {CompositeAvailableCapacityGroup-ExtIEs} } OPTIONAL,
    ...
}

CompositeAvailableCapacityGroup-ExtIEs X2AP-PROTOCOL-EXTENSION ::= {
    ...
}

Correlation-ID ::= OCTET STRING (SIZE (4))

COUNTvalue ::= SEQUENCE {
    pDCP-SN                 PDCP-SN,
    hFN                     HFN,
    iE-Extensions           ProtocolExtensionContainer { {COUNTvalue-ExtIEs} } OPTIONAL,
    ...
}

COUNTvalue-ExtIEs X2AP-PROTOCOL-EXTENSION ::= {
    ...
}

COUNTValueExtended ::= SEQUENCE {
    pDCP-SNExtended         PDCP-SNExtended,
    hFNModified             HFNModified,
    iE-Extensions           ProtocolExtensionContainer { {COUNTValueExtended-ExtIEs} } OPTIONAL,
    ...
}

COUNTValueExtended-ExtIEs X2AP-PROTOCOL-EXTENSION ::= {
    ...
}

COUNTvaluePDCP-SNlength18 ::= SEQUENCE {
    pDCP-SNlength18         PDCP-SNlength18,
    hFNforPDCP-SNlength18   HFNforPDCP-SNlength18,
    iE-Extensions           ProtocolExtensionContainer { {COUNTvaluePDCP-SNlength18-ExtIEs} } OPTIONAL,
    ...
}

COUNTvaluePDCP-SNlength18-ExtIEs X2AP-PROTOCOL-EXTENSION ::= {
    ...
}

CoverageModificationList ::= SEQUENCE (SIZE (1..maxCellineNB)) OF CoverageModification-Item

CoverageModification-Item ::= SEQUENCE {
    eCGI                            ECGI,
    coverageState                   INTEGER (0..15, ...),
    cellDeploymentStatusIndicator   CellDeploymentStatusIndicator           OPTIONAL,
    cellReplacingInfo               CellReplacingInfo                       OPTIONAL,
-- Included in case the Cell Deployment Status Indicator IE is present
    ...
}

CPTransportLayerInformation     ::= CHOICE {
    endpointIPAddress                       TransportLayerAddress,
    endpointIPAddressAndPort                    TransportLayerAddressAndPort,
    ...
}

CriticalityDiagnostics ::= SEQUENCE {
    procedureCode                   ProcedureCode                   OPTIONAL,
    triggeringMessage               TriggeringMessage               OPTIONAL,
    procedureCriticality            Criticality                     OPTIONAL,
    iEsCriticalityDiagnostics       CriticalityDiagnostics-IE-List  OPTIONAL,
    iE-Extensions                   ProtocolExtensionContainer { {CriticalityDiagnostics-ExtIEs} }  OPTIONAL,
    ...
}


CriticalityDiagnostics-ExtIEs X2AP-PROTOCOL-EXTENSION ::= {
    ...
}

CriticalityDiagnostics-IE-List ::= SEQUENCE (SIZE (1..maxNrOfErrors)) OF
    SEQUENCE {
        iECriticality           Criticality,
        iE-ID                   ProtocolIE-ID,
        typeOfError             TypeOfError,
        iE-Extensions           ProtocolExtensionContainer { {CriticalityDiagnostics-IE-List-ExtIEs} } OPTIONAL,
        ...
}

CriticalityDiagnostics-IE-List-ExtIEs X2AP-PROTOCOL-EXTENSION ::= {
    ...
}

CRNTI ::= BIT STRING (SIZE (16))

CSGMembershipStatus ::= ENUMERATED {
    member,
    not-member
}

CSG-Id ::= BIT STRING (SIZE (27))

CSIReportList ::= SEQUENCE (SIZE(1..maxUEReport)) OF
    SEQUENCE {
        uEID                            UEID,
        cSIReportPerCSIProcess          CSIReportPerCSIProcess,
        iE-Extensions                   ProtocolExtensionContainer { {CSIReportList-ExtIEs} } OPTIONAL,
        ...
    }

CSIReportList-ExtIEs X2AP-PROTOCOL-EXTENSION ::= {
    ...
}

CSIReportPerCSIProcess ::= SEQUENCE (SIZE(1.. maxCSIProcess)) OF
    SEQUENCE {
        cSIProcessConfigurationIndex    INTEGER (1..7, ...),
        cSIReportPerCSIProcessItem      CSIReportPerCSIProcessItem,
        iE-Extensions                   ProtocolExtensionContainer { {CSIReportPerCSIProcess-ExtIEs} } OPTIONAL,
        ...
    }

CSIReportPerCSIProcess-ExtIEs X2AP-PROTOCOL-EXTENSION ::= {
    ...
}

CSIReportPerCSIProcessItem ::= SEQUENCE (SIZE(1.. maxCSIReport)) OF
    SEQUENCE {
        rI                              INTEGER (1..8, ...),
        widebandCQI                     WidebandCQI,
        subbandSize                     SubbandSize,
        subbandCQIList                  SubbandCQIList  OPTIONAL,
        iE-Extensions                   ProtocolExtensionContainer { {CSIReportPerCSIProcessItem-ExtIEs} } OPTIONAL,
        ...
    }

CSIReportPerCSIProcessItem-ExtIEs X2AP-PROTOCOL-EXTENSION ::= {
    ...
}

CyclicPrefixDL ::= ENUMERATED {
    normal,
    extended,
    ...
}

CyclicPrefixUL ::= ENUMERATED {
    normal,
    extended,
    ...
}

CHOtrigger ::= ENUMERATED {
    cho-initiation,
    cho-replace,
    ...
}

CHOinformation-REQ ::= SEQUENCE {
    cho-trigger                     CHOtrigger,
    new-eNB-UE-X2AP-ID              UE-X2AP-ID                                          OPTIONAL
        -- This IE shall be present if the cho-trigger IE is present and set to "CHO-replace" --,
    new-eNB-UE-X2AP-ID-Extension    UE-X2AP-ID-Extension                                OPTIONAL,
    cHO-EstimatedArrivalProbability CHO-Probability                                     OPTIONAL,
    iE-Extensions               ProtocolExtensionContainer { { CHOinformation-REQ-ExtIEs} } OPTIONAL,
    ...
}

CHOinformation-REQ-ExtIEs X2AP-PROTOCOL-EXTENSION ::={
    {ID id-CHOTimeBasedInformation  CRITICALITY reject  EXTENSION CHOTimeBasedInformation       PRESENCE optional},
    ...
}

CHOTimeBasedInformation ::= SEQUENCE {
    cHO-HOWindowStart           CHO-HandoverWindowStart,
    cHO-HOWindowDuration        CHO-HandoverWindowDuration,
    iE-Extensions               ProtocolExtensionContainer { {CHOTimeBasedInformation-ExtIEs} } OPTIONAL,
    ...
}

CHOTimeBasedInformation-ExtIEs  X2AP-PROTOCOL-EXTENSION ::= {
    ...
}

CHOinformation-ACK ::= SEQUENCE {
    requestedTargetCellID           ECGI,
    maxCHOpreparations              MaxCHOpreparations                                          OPTIONAL,
    iE-Extensions                   ProtocolExtensionContainer { { CHOinformation-ACK-ExtIEs} } OPTIONAL,
    ...
}

CHOinformation-ACK-ExtIEs X2AP-PROTOCOL-EXTENSION ::={
    ...
}


CandidateCellsToBeCancelledList ::= SEQUENCE (SIZE (1..maxnoofCellsinCHO)) OF ECGI

CHO-Probability ::= INTEGER (1..100)

CHO-HandoverWindowStart ::= INTEGER (0..1048575)

CHO-HandoverWindowDuration ::= INTEGER (1..6000)

CHOinformation-AddReq ::= SEQUENCE {
    source-eNB-ID               GlobalENB-ID,
    source-eNB-UE-X2AP-ID       UE-X2AP-ID,
    source-eNB-UE-X2AP-ID-Ext   UE-X2AP-ID-Extension                                            OPTIONAL,
    cHO-EstimatedArrivalProbability     CHO-Probability                                                 OPTIONAL,
    iE-Extensions                   ProtocolExtensionContainer { { CHOinformation-AddReq-ExtIEs} }  OPTIONAL,
    ...
}

CHOinformation-AddReq-ExtIEs X2AP-PROTOCOL-EXTENSION ::={
    ...
}


CHOinformation-ModReq ::= SEQUENCE {
    conditionalReconfig                 ENUMERATED {intra-mn-cho, ...},
    cHO-EstimatedArrivalProbability     CHO-Probability                                                 OPTIONAL,
    iE-Extensions                   ProtocolExtensionContainer { { CHOinformation-ModReq-ExtIEs} }  OPTIONAL,
    ...
}

CHOinformation-ModReq-ExtIEs X2AP-PROTOCOL-EXTENSION ::={
    ...
}


CSI-RSTransmissionIndication ::= ENUMERATED {
    activated,
    deactivated,
    ...
}

-- D


DataTrafficResources ::= BIT STRING (SIZE(6..17600))

DataTrafficResourceIndication ::= SEQUENCE {
    activationSFN                   INTEGER (0..1023),
    sharedResourceType              SharedResourceType,
    reservedSubframePattern         ReservedSubframePattern OPTIONAL,
    iE-Extensions                   ProtocolExtensionContainer { {DataTrafficResourceIndication-ExtIEs} } OPTIONAL,
...
}

DataTrafficResourceIndication-ExtIEs X2AP-PROTOCOL-EXTENSION ::= {
    ...
}

DAPSRequestInfo ::= SEQUENCE {
    dAPSIndicator               ENUMERATED {daps-HO-required, ...},
    iE-Extensions               ProtocolExtensionContainer { {DAPSRequestInfo-ExtIEs} } OPTIONAL,
    ...
}

DAPSRequestInfo-ExtIEs X2AP-PROTOCOL-EXTENSION ::= {
    ...
}
DAPSResponseInfo ::= SEQUENCE {
    dAPSResponseIndicator                   ENUMERATED { daps-HO-accepted, daps-HO-not-accepted,...},
    iE-Extensions               ProtocolExtensionContainer { { DAPSResponseInfo-ExtIEs} } OPTIONAL,
    ...
}

DAPSResponseInfo-ExtIEs X2AP-PROTOCOL-EXTENSION ::= {
    ...
}

DeactivationIndication::= ENUMERATED {
    deactivated,
    ...
}

DeliveryStatus ::= SEQUENCE {
    highestSuccessDeliveredPDCPSN       INTEGER (0..4095),
    iE-Extensions       ProtocolExtensionContainer { {DeliveryStatus-ExtIEs} } OPTIONAL,
    ...
}

DeliveryStatus-ExtIEs X2AP-PROTOCOL-EXTENSION ::= {
    ...
}

DesiredActNotificationLevel ::= ENUMERATED {none, e-rab, ue-level, ...}

DirectForwardingPathAvailability ::= ENUMERATED {direct-path-available, ...}

DL-ABS-status::= INTEGER (0..100)

DL-Forwarding ::= ENUMERATED {
    dL-forwardingProposed,
    ...
}

DL-GBR-PRB-usage::= INTEGER (0..100)

DL-GBR-PRB-usage-for-MIMO::= INTEGER (0..100)

DL-non-GBR-PRB-usage::= INTEGER (0..100)

DL-non-GBR-PRB-usage-for-MIMO::= INTEGER (0..100)

DLResourceBitmapULandDLSharing ::= DataTrafficResources

DLResourcesULandDLSharing ::= CHOICE {
unchanged           NULL,
    changed             DLResourceBitmapULandDLSharing,
    ...
}

DL-scheduling-PDCCH-CCE-usage::= INTEGER (0..100)

DL-Total-PRB-usage::= INTEGER (0..100)

DL-Total-PRB-usage-for-MIMO::= INTEGER (0..100)

DRB-ID ::= INTEGER (1..32)

DuplicationActivation::= ENUMERATED {active, inactive, ...}

DynamicDLTransmissionInformation ::= CHOICE {
    naics-active            DynamicNAICSInformation,
    naics-inactive          NULL,
    ...
}

DynamicNAICSInformation ::= SEQUENCE {
    transmissionModes                   BIT STRING (SIZE(8))                                                OPTIONAL,
    pB-information                      INTEGER(0..3)                                                       OPTIONAL,
    pA-list                             SEQUENCE (SIZE(0..maxnoofPA)) OF PA-Values,
    iE-Extensions                       ProtocolExtensionContainer { {DynamicNAICSInformation-ExtIEs} } OPTIONAL,
    ...
}

DynamicNAICSInformation-ExtIEs X2AP-PROTOCOL-EXTENSION ::= {
    ...
}

-- E

EARFCN ::= INTEGER (0..maxEARFCN)

EARFCNExtension ::= INTEGER(maxEARFCNPlusOne..newmaxEARFCN, ...)

ECGI ::= SEQUENCE {
    pLMN-Identity               PLMN-Identity,
    eUTRANcellIdentifier        EUTRANCellIdentifier,
    iE-Extensions               ProtocolExtensionContainer { {ECGI-ExtIEs} } OPTIONAL,
    ...
}

ECGI-ExtIEs X2AP-PROTOCOL-EXTENSION ::= {
    ...
}

EndcSONConfigurationTransfer ::= OCTET STRING

EnhancedRNTP ::= SEQUENCE {
    enhancedRNTPBitmap          BIT STRING (SIZE(12..8800, ...)),
    rNTP-High-Power-Threshold   RNTP-Threshold,
    enhancedRNTPStartTime       EnhancedRNTPStartTime OPTIONAL,
    iE-Extensions               ProtocolExtensionContainer { {EnhancedRNTP-ExtIEs} } OPTIONAL,
    ...
}

EnhancedRNTP-ExtIEs X2AP-PROTOCOL-EXTENSION ::= {
    ...
}

EnhancedRNTPStartTime ::= SEQUENCE {
        startSFN                INTEGER (0..1023, ...),
        startSubframeNumber     INTEGER (0..9, ...),
        iE-Extensions           ProtocolExtensionContainer { {EnhancedRNTPStartTime-ExtIEs} } OPTIONAL,
        ...
    }

EnhancedRNTPStartTime-ExtIEs X2AP-PROTOCOL-EXTENSION ::= {
    ...
}

ENB-ID ::= CHOICE {
    macro-eNB-ID    BIT STRING (SIZE (20)),
    home-eNB-ID     BIT STRING (SIZE (28)),
    ... ,
    short-Macro-eNB-ID      BIT STRING (SIZE(18)),
    long-Macro-eNB-ID       BIT STRING (SIZE(21))
}

EncryptionAlgorithms ::= BIT STRING (SIZE (16, ...))

EN-DC-ResourceConfiguration ::= SEQUENCE {
    pDCPatSgNB      ENUMERATED {present, not-present, ...},
    mCGresources    ENUMERATED {present, not-present, ...},
    sCGresources    ENUMERATED {present, not-present, ...},
    iE-Extensions                   ProtocolExtensionContainer { {EN-DC-ResourceConfigurationExtIEs} }  OPTIONAL,
    ...
}

EN-DC-ResourceConfigurationExtIEs X2AP-PROTOCOL-EXTENSION ::= {
    ...
}

EPCHandoverRestrictionListContainer ::= OCTET STRING
-- This octets of the OCTET STRING contain the Handover Restriction List IE as specified in TS 36.413 [4]. --

EPLMNs ::= SEQUENCE (SIZE(1..maxnoofEPLMNs)) OF PLMN-Identity

ERABActivityNotifyItemList ::= SEQUENCE (SIZE (0..maxnoofBearers)) OF ERABActivityNotifyItem

ERABActivityNotifyItem ::= SEQUENCE {
    e-RAB-ID                        E-RAB-ID,
    activityReport                  UserPlaneTrafficActivityReport,
    iE-Extensions                   ProtocolExtensionContainer { {ERABActivityNotifyItem-ExtIEs} }  OPTIONAL,
    ...
}

ERABActivityNotifyItem-ExtIEs X2AP-PROTOCOL-EXTENSION ::= {
    ...
}

E-RAB-ID ::= INTEGER (0..15, ...)

E-RAB-Level-QoS-Parameters ::= SEQUENCE {
    qCI                             QCI,
    allocationAndRetentionPriority  AllocationAndRetentionPriority,
    gbrQosInformation               GBR-QosInformation                                                  OPTIONAL,
    iE-Extensions                   ProtocolExtensionContainer { {E-RAB-Level-QoS-Parameters-ExtIEs} }  OPTIONAL,
    ...
}

E-RAB-Level-QoS-Parameters-ExtIEs X2AP-PROTOCOL-EXTENSION ::= {
-- Extended for introduction of downlink and uplink packet loss rate for enhanced Voice performance –
    { ID id-DownlinkPacketLossRate          CRITICALITY ignore  EXTENSION Packet-LossRate       PRESENCE optional}|
    { ID id-UplinkPacketLossRate            CRITICALITY ignore  EXTENSION Packet-LossRate       PRESENCE optional},
    ...
}

E-RAB-List ::= SEQUENCE (SIZE(1.. maxnoofBearers)) OF ProtocolIE-Single-Container { {E-RAB-ItemIEs} }

E-RAB-ItemIEs   X2AP-PROTOCOL-IES ::= {
    { ID id-E-RAB-Item   CRITICALITY ignore     TYPE E-RAB-Item     PRESENCE mandatory },
    ...
}

E-RAB-Item ::= SEQUENCE {
    e-RAB-ID                E-RAB-ID,
    cause                       Cause,
    iE-Extensions               ProtocolExtensionContainer { {E-RAB-Item-ExtIEs} } OPTIONAL,
    ...
}

E-RAB-Item-ExtIEs X2AP-PROTOCOL-EXTENSION ::= {
    ...
}

E-RABsSubjectToEarlyStatusTransfer-List ::= SEQUENCE (SIZE (1.. maxnoofBearers)) OF E-RABsSubjectToEarlyStatusTransfer-Item

E-RABsSubjectToEarlyStatusTransfer-Item ::= SEQUENCE {
    e-RAB-ID                                            E-RAB-ID,
    fIRST-DL-COUNTValue                                 COUNTvalue,
    fIRST-DL-COUNTValueExtended                         COUNTValueExtended                                                  OPTIONAL,
    fIRST-DL-COUNTValueforPDCPSNLength18                COUNTvaluePDCP-SNlength18                                                   OPTIONAL,
    iE-Extension        ProtocolExtensionContainer { { E-RABsSubjectToEarlyStatusTransfer-Item-ExtIEs} }    OPTIONAL,
    ...
}

E-RABsSubjectToEarlyStatusTransfer-Item-ExtIEs X2AP-PROTOCOL-EXTENSION ::= {
    ...
}

E-RABsSubjectToDLDiscarding-List ::= SEQUENCE (SIZE (1.. maxnoofBearers)) OF E-RABsSubjectToDLDiscarding-Item

E-RABsSubjectToDLDiscarding-Item ::= SEQUENCE {
    e-RAB-ID                                            E-RAB-ID,
    dISCARD-DL-COUNTValue                               COUNTvalue,
    dISCARD-DL-COUNTValueExtended                       COUNTValueExtended                                                  OPTIONAL,
    dISCARD-DL-COUNTValueforPDCPSNLength18              COUNTvaluePDCP-SNlength18                                                   OPTIONAL,
    iE-Extension        ProtocolExtensionContainer { { E-RABsSubjectToDLDiscarding-Item-ExtIEs} }                   OPTIONAL,
    ...
}

E-RABsSubjectToDLDiscarding-Item-ExtIEs X2AP-PROTOCOL-EXTENSION ::= {
    ...
}


E-RABUsageReportList ::= SEQUENCE (SIZE(1..maxnooftimeperiods)) OF ProtocolIE-Single-Container { {E-RABUsageReport-ItemIEs} }

E-RABUsageReport-ItemIEs X2AP-PROTOCOL-IES ::= {
    { ID id-E-RABUsageReport-Item    CRITICALITY ignore     TYPE E-RABUsageReport-Item  PRESENCE mandatory },
    ...
}

E-RABUsageReport-Item ::= SEQUENCE {
    startTimeStamp              OCTET STRING (SIZE(4)),
    endTimeStamp                    OCTET STRING (SIZE(4)),
    usageCountUL                    INTEGER (0..18446744073709551615),
    usageCountDL                    INTEGER (0..18446744073709551615),
    iE-Extensions               ProtocolExtensionContainer { {E-RABUsageReport-Item-ExtIEs} } OPTIONAL,
...
}

E-RABUsageReport-Item-ExtIEs X2AP-PROTOCOL-EXTENSION ::= {
    ...
}

Ethernet-Type ::= ENUMERATED {
    true,
    ...
}

EUTRA-Mode-Info ::= CHOICE {
    fDD     FDD-Info,
    tDD     TDD-Info,
    ...
}

EUTRANCellIdentifier ::= BIT STRING (SIZE (28))

EUTRANTraceID       ::= OCTET STRING (SIZE (8))

EventType ::= ENUMERATED{
    change-of-serving-cell,
    ...
}

ExpectedUEBehaviour ::= SEQUENCE {
    expectedActivity        ExpectedUEActivityBehaviour OPTIONAL,
    expectedHOInterval      ExpectedHOInterval          OPTIONAL,
    iE-Extensions           ProtocolExtensionContainer { {ExpectedUEBehaviour-ExtIEs} } OPTIONAL,
    ...
}

ExpectedUEBehaviour-ExtIEs X2AP-PROTOCOL-EXTENSION ::= {
    ...
}

ExpectedUEActivityBehaviour ::= SEQUENCE {
    expectedActivityPeriod                  ExpectedActivityPeriod                  OPTIONAL,
    expectedIdlePeriod                      ExpectedIdlePeriod                      OPTIONAL,
    sourceofUEActivityBehaviourInformation  SourceOfUEActivityBehaviourInformation  OPTIONAL,
    iE-Extensions       ProtocolExtensionContainer { {ExpectedUEActivityBehaviour-ExtIEs} } OPTIONAL,
    ...
}

ExpectedUEActivityBehaviour-ExtIEs X2AP-PROTOCOL-EXTENSION ::= {
    ...
}

ExpectedActivityPeriod ::= INTEGER (1..30|40|50|60|80|100|120|150|180|181,...)

ExpectedIdlePeriod ::= INTEGER (1..30|40|50|60|80|100|120|150|180|181,...)

ExpectedHOInterval ::= ENUMERATED {
    sec15, sec30, sec60, sec90, sec120, sec180, long-time,
    ...
}

ExtendedULInterferenceOverloadInfo ::= SEQUENCE {
    associatedSubframes                         BIT STRING (SIZE (5)),
    extended-ul-InterferenceOverloadIndication  UL-InterferenceOverloadIndication,
    iE-Extensions                               ProtocolExtensionContainer { {ExtendedULInterferenceOverloadInfo-ExtIEs} } OPTIONAL,
    ...
}

ExtendedULInterferenceOverloadInfo-ExtIEs X2AP-PROTOCOL-EXTENSION ::= {
    ...
}

ExtendedBitRate ::= INTEGER (10000000001..4000000000000,...)

-- F

F1CTrafficContainer ::= OCTET STRING

FastMCGRecovery ::= SEQUENCE {
    rrcContainer                RRCContainer            OPTIONAL,
    iE-Extensions               ProtocolExtensionContainer { {FastMCGRecovery-ExtIEs} } OPTIONAL,
    ...
}

FastMCGRecovery-ExtIEs X2AP-PROTOCOL-EXTENSION ::= {
    ...
}

FDD-Info ::= SEQUENCE {
    uL-EARFCN                       EARFCN,
    dL-EARFCN                       EARFCN,
    uL-Transmission-Bandwidth       Transmission-Bandwidth,
    dL-Transmission-Bandwidth       Transmission-Bandwidth,
    iE-Extensions               ProtocolExtensionContainer { {FDD-Info-ExtIEs} } OPTIONAL,
    ...
}

FDD-Info-ExtIEs X2AP-PROTOCOL-EXTENSION ::= {
    { ID id-UL-EARFCNExtension                      CRITICALITY reject  EXTENSION EARFCNExtension                                   PRESENCE optional}|
    { ID id-DL-EARFCNExtension                      CRITICALITY reject  EXTENSION EARFCNExtension                                   PRESENCE optional}|
    { ID id-OffsetOfNbiotChannelNumberToDL-EARFCN   CRITICALITY reject  EXTENSION OffsetOfNbiotChannelNumberToEARFCN        PRESENCE optional}|
    { ID id-OffsetOfNbiotChannelNumberToUL-EARFCN   CRITICALITY reject  EXTENSION OffsetOfNbiotChannelNumberToEARFCN        PRESENCE optional}|
    { ID id-NRS-NSSS-PowerOffset                    CRITICALITY ignore  EXTENSION NRS-NSSS-PowerOffset                          PRESENCE optional}|
    { ID id-NSSS-NumOccasionDifferentPrecoder       CRITICALITY ignore  EXTENSION NSSS-NumOccasionDifferentPrecoder         PRESENCE optional},
    ...
}

FDD-InfoNeighbourServedNRCell-Information ::= SEQUENCE {
    ul-NRFreqInfo           NRFreqInfo,
    dl-NRFreqInfo           NRFreqInfo,
    iE-Extensions           ProtocolExtensionContainer { {FDD-InfoNeighbourServedNRCell-Information-ExtIEs} }       OPTIONAL,
    ...
}

FDD-InfoNeighbourServedNRCell-Information-ExtIEs X2AP-PROTOCOL-EXTENSION ::= {
    { ID id-ULCarrierList   CRITICALITY ignore  EXTENSION NRCarrierList         PRESENCE optional },
    ...
}

FiveQI ::= INTEGER (0..255, ...)

ForbiddenInterRATs ::= ENUMERATED {
    all,
    geran,
    utran,
    cdma2000,
    ...,
    geranandutran,
    cdma2000andutran

}

ForbiddenTAs ::= SEQUENCE (SIZE(1.. maxnoofEPLMNsPlusOne)) OF ForbiddenTAs-Item

ForbiddenTAs-Item ::= SEQUENCE {
    pLMN-Identity       PLMN-Identity,
    forbiddenTACs       ForbiddenTACs,
    iE-Extensions       ProtocolExtensionContainer { {ForbiddenTAs-Item-ExtIEs} } OPTIONAL,
    ...
}

ForbiddenTAs-Item-ExtIEs X2AP-PROTOCOL-EXTENSION ::= {
    ...
}

ForbiddenTACs ::= SEQUENCE (SIZE(1..maxnoofForbTACs)) OF TAC

ForbiddenLAs ::= SEQUENCE (SIZE(1..maxnoofEPLMNsPlusOne)) OF ForbiddenLAs-Item

ForbiddenLAs-Item ::= SEQUENCE {
    pLMN-Identity       PLMN-Identity,
    forbiddenLACs       ForbiddenLACs,
    iE-Extensions       ProtocolExtensionContainer { {ForbiddenLAs-Item-ExtIEs} } OPTIONAL,
    ...
}

ForbiddenLAs-Item-ExtIEs X2AP-PROTOCOL-EXTENSION ::= {
    ...
}

ForbiddenLACs ::= SEQUENCE (SIZE(1..maxnoofForbLACs)) OF LAC

Fourframes ::= BIT STRING (SIZE (24))

FreqBandIndicator ::= INTEGER (1..256, ...)

FreqBandIndicatorPriority ::= ENUMERATED {
    not-broadcasted,
    broadcasted,
    ...
}


FreqBandNrItem ::= SEQUENCE {
    freqBandIndicatorNr             INTEGER (1..1024,...),
    supportedSULBandList    SEQUENCE (SIZE(0..maxnoofNrCellBands)) OF SupportedSULFreqBandItem,
    iE-Extensions               ProtocolExtensionContainer { {FreqBandNrItem-ExtIEs} } OPTIONAL,
    ...
}

FreqBandNrItem-ExtIEs X2AP-PROTOCOL-EXTENSION ::= {
    ...
}

FrequencyShift7p5khz ::= ENUMERATED {false, true, ...}


-- G

GBR-QosInformation ::= SEQUENCE {
    e-RAB-MaximumBitrateDL          BitRate,
    e-RAB-MaximumBitrateUL          BitRate,
    e-RAB-GuaranteedBitrateDL       BitRate,
    e-RAB-GuaranteedBitrateUL       BitRate,
    iE-Extensions                   ProtocolExtensionContainer { {GBR-QosInformation-ExtIEs} } OPTIONAL,
    ...
}

GBR-QosInformation-ExtIEs X2AP-PROTOCOL-EXTENSION ::= {
-- Extension for maximum bitrate > 10Gbps --
    { ID id-extended-e-RAB-MaximumBitrateDL     CRITICALITY ignore  EXTENSION ExtendedBitRate   PRESENCE optional}|
    { ID id-extended-e-RAB-MaximumBitrateUL     CRITICALITY ignore  EXTENSION ExtendedBitRate   PRESENCE optional}|
    { ID id-extended-e-RAB-GuaranteedBitrateDL  CRITICALITY ignore  EXTENSION ExtendedBitRate   PRESENCE optional}|
    { ID id-extended-e-RAB-GuaranteedBitrateUL  CRITICALITY ignore  EXTENSION ExtendedBitRate   PRESENCE optional},
    ...
}

GlobalENB-ID ::= SEQUENCE {
    pLMN-Identity           PLMN-Identity,
    eNB-ID                  ENB-ID,
    iE-Extensions           ProtocolExtensionContainer { {GlobalENB-ID-ExtIEs} } OPTIONAL,
    ...
}

GlobalENB-ID-ExtIEs X2AP-PROTOCOL-EXTENSION ::= {
    ...
}

GlobalGNB-ID ::= SEQUENCE {
    pLMN-Identity           PLMN-Identity,
    gNB-ID                  GNB-ID,
    iE-Extensions           ProtocolExtensionContainer { {GlobalGNB-ID-ExtIEs} } OPTIONAL,
    ...
}

GlobalGNB-ID-ExtIEs X2AP-PROTOCOL-EXTENSION ::= {
    ...
}

Global-RAN-NODE-ID ::= CHOICE {
    gNB                     GlobalGNB-ID,
    choice-extension        ProtocolIE-Single-Container { { Global-RAN-NODE-ID-ExtIEs} }
}

Global-RAN-NODE-ID-ExtIEs X2AP-PROTOCOL-IES ::= {
    ...
}

GNBOverloadInformation ::= ENUMERATED {overloaded, not-overloaded, ...}

GTPTLAs ::= SEQUENCE (SIZE(1.. maxnoofGTPTLAs)) OF  GTPTLA-Item


GTPTLA-Item ::= SEQUENCE {
    gTPTransportLayerAddresses          TransportLayerAddress,
    iE-Extensions                       ProtocolExtensionContainer { { GTPTLA-Item-ExtIEs } } OPTIONAL,
    ...
}

GTPTLA-Item-ExtIEs X2AP-PROTOCOL-EXTENSION ::= {
    ...
}

GTPtunnelEndpoint ::= SEQUENCE {
    transportLayerAddress           TransportLayerAddress,
    gTP-TEID                        GTP-TEI,
    iE-Extensions                   ProtocolExtensionContainer { {GTPtunnelEndpoint-ExtIEs} } OPTIONAL,
    ...
}

GTPtunnelEndpoint-ExtIEs X2AP-PROTOCOL-EXTENSION ::= {
    {ID id-QoS-Mapping-Information  CRITICALITY reject  EXTENSION QoS-Mapping-Information   PRESENCE optional},
    ...
}

GTP-TEI                 ::= OCTET STRING (SIZE (4))

GUGroupIDList       ::= SEQUENCE (SIZE (1..maxPools)) OF GU-Group-ID


GU-Group-ID         ::= SEQUENCE {
    pLMN-Identity       PLMN-Identity,
    mME-Group-ID        MME-Group-ID,
    iE-Extensions       ProtocolExtensionContainer { {GU-Group-ID-ExtIEs} } OPTIONAL,
    ...
}

GU-Group-ID-ExtIEs X2AP-PROTOCOL-EXTENSION ::= {
    ...
}


GUMMEI          ::= SEQUENCE {

    gU-Group-ID     GU-Group-ID,
    mME-Code            MME-Code,
    iE-Extensions                   ProtocolExtensionContainer { {GUMMEI-ExtIEs} } OPTIONAL,
    ...
}

GUMMEI-ExtIEs X2AP-PROTOCOL-EXTENSION ::= {
    ...
}

GNB-ID ::= CHOICE {
    gNB-ID  BIT STRING (SIZE (22..32)),
    ...
}


-- H

HandoverReportType ::= ENUMERATED {
    hoTooEarly,
    hoToWrongCell,
    ...,
    interRATpingpong,
    interSystemPingpong
}

HandoverRestrictionList ::= SEQUENCE {
    servingPLMN                 PLMN-Identity,
    equivalentPLMNs             EPLMNs                  OPTIONAL,
    forbiddenTAs                ForbiddenTAs            OPTIONAL,
    forbiddenLAs                ForbiddenLAs            OPTIONAL,
    forbiddenInterRATs          ForbiddenInterRATs      OPTIONAL,
    iE-Extensions               ProtocolExtensionContainer { {HandoverRestrictionList-ExtIEs} } OPTIONAL,
    ...
}

HandoverRestrictionList-ExtIEs X2AP-PROTOCOL-EXTENSION ::= {
    { ID id-NRrestrictioninEPSasSecondaryRAT            CRITICALITY ignore  EXTENSION NRrestrictioninEPSasSecondaryRAT          PRESENCE optional}|
    { ID id-CNTypeRestrictions                      CRITICALITY ignore  EXTENSION CNTypeRestrictions                                PRESENCE optional}|
    { ID id-NRrestrictionin5GS                      CRITICALITY ignore  EXTENSION NRrestrictionin5GS                                PRESENCE optional}|
    { ID id-LastNG-RANPLMNIdentity                  CRITICALITY ignore  EXTENSION PLMN-Identity                                     PRESENCE optional}|
    { ID id-UnlicensedSpectrumRestriction           CRITICALITY ignore  EXTENSION UnlicensedSpectrumRestriction             PRESENCE optional}|
    { ID id-RAT-Restrictions                        CRITICALITY ignore  EXTENSION RAT-Restrictions                              PRESENCE optional},
    ...
}

HFN ::= INTEGER (0..1048575)

HFNModified ::= INTEGER (0..131071)

HFNforPDCP-SNlength18 ::= INTEGER (0..16383)

HWLoadIndicator ::= SEQUENCE {
    dLHWLoadIndicator           LoadIndicator,
    uLHWLoadIndicator           LoadIndicator,
    iE-Extensions               ProtocolExtensionContainer { {HWLoadIndicator-ExtIEs} } OPTIONAL,
    ...
}

HWLoadIndicator-ExtIEs X2AP-PROTOCOL-EXTENSION ::= {
    ...
}


-- I


IABNodeIndication ::= ENUMERATED {true,...}

IABAuthorized ::= ENUMERATED {
    authorized,
    not-authorized,
    ...
}


IMSvoiceEPSfallbackfrom5G ::= ENUMERATED {
    true,
    ...
}

IntegrityProtectionAlgorithms ::= BIT STRING (SIZE (16, ...))

IntegrityProtectionIndication ::= ENUMERATED {
    required,
    preferred,
    notneeded,
    ...
}

IntegrityProtectionResult ::= ENUMERATED {
    performed,
    notperformed,
    ...
}

IntendedTDD-DL-ULConfiguration-NR ::= OCTET STRING

InterfaceInstanceIndication ::= INTEGER (0..255, ...)

InterfacesToTrace ::= BIT STRING (SIZE (8))

InvokeIndication ::= ENUMERATED{
    abs-information,
    ...,
    naics-information-start,
    naics-information-stop
}

-- J
-- K

Key-eNodeB-Star ::= BIT STRING (SIZE(256))

-- L

LastVisitedPSCell-Item ::= OCTET STRING

LAC                 ::= OCTET STRING (SIZE (2)) --(EXCEPT ('0000'H|'FFFE'H))

LastVisitedCell-Item ::= CHOICE {
    e-UTRAN-Cell                    LastVisitedEUTRANCellInformation,
    uTRAN-Cell                      LastVisitedUTRANCellInformation,
    gERAN-Cell                      LastVisitedGERANCellInformation,
    ...,
    nG-RAN-Cell                     LastVisitedNGRANCellInformation
}

LastVisitedEUTRANCellInformation ::= SEQUENCE {
    global-Cell-ID                  ECGI,
    cellType                        CellType,
    time-UE-StayedInCell            Time-UE-StayedInCell,
    iE-Extensions                   ProtocolExtensionContainer { {LastVisitedEUTRANCellInformation-ExtIEs} } OPTIONAL,
    ...
}

LastVisitedEUTRANCellInformation-ExtIEs X2AP-PROTOCOL-EXTENSION ::= {
-- Extension for Rel-11 to support enhanced granularity for time UE stayed in cell --
    { ID id-Time-UE-StayedInCell-EnhancedGranularity    CRITICALITY ignore  EXTENSION Time-UE-StayedInCell-EnhancedGranularity  PRESENCE optional}|
    { ID id-HO-cause                                    CRITICALITY ignore  EXTENSION Cause                                                 PRESENCE optional}|
    { ID id-PSCell-UE-HistoryInformation            CRITICALITY ignore  EXTENSION PSCell-UE-HistoryInformation                          PRESENCE optional},
    ...
}

LastVisitedGERANCellInformation ::= CHOICE {
    undefined                       NULL,
    ...
}

LastVisitedNGRANCellInformation ::= OCTET STRING

LastVisitedUTRANCellInformation ::= OCTET STRING

LCID ::= INTEGER(1..32, ...)

LHN-ID ::= OCTET STRING(SIZE (32..256))

Links-to-log ::= ENUMERATED {uplink, downlink, both-uplink-and-downlink, ...}

LoadIndicator ::= ENUMERATED {
    lowLoad,
    mediumLoad,
    highLoad,
    overLoad,
    ...
}

LocationInformationSgNB ::= SEQUENCE {
    pSCell-id           NRCGI,
    iE-Extensions       ProtocolExtensionContainer { {LocationInformationSgNB-ExtIEs} } OPTIONAL,
    ...
}

LocationInformationSgNB-ExtIEs X2AP-PROTOCOL-EXTENSION ::={
    ...
}

LocationInformationSgNBReporting ::= ENUMERATED {
    pSCell,
    ...
}

LocationReportingInformation ::= SEQUENCE {
    eventType       EventType,
    reportArea      ReportArea,
    iE-Extensions       ProtocolExtensionContainer { {LocationReportingInformation-ExtIEs} } OPTIONAL,
    ...
}

LocationReportingInformation-ExtIEs X2AP-PROTOCOL-EXTENSION ::={
    { ID id-AdditionLocationInformation CRITICALITY ignore  EXTENSION AdditionLocationInformation   PRESENCE optional},
    ...
}

LowerLayerPresenceStatusChange ::= ENUMERATED {
    release-lower-layers,
    re-establish-lower-layers,
    suspend-lower-layers,
    resume-lower-layers,
    ...
}

-- M

M1PeriodicReporting ::= SEQUENCE {
    reportInterval              ReportIntervalMDT,
    reportAmount                ReportAmountMDT,
    iE-Extensions               ProtocolExtensionContainer { {M1PeriodicReporting-ExtIEs} } OPTIONAL,
    ...
}

M1PeriodicReporting-ExtIEs X2AP-PROTOCOL-EXTENSION ::= {
    ...
}

M1ReportingTrigger::= ENUMERATED{
    periodic,
    a2eventtriggered,
    ...,
    a2eventtriggered-periodic
}

M1ThresholdEventA2 ::= SEQUENCE {
    measurementThreshold        MeasurementThresholdA2,
    iE-Extensions               ProtocolExtensionContainer { {M1ThresholdEventA2-ExtIEs} } OPTIONAL,
    ...
}

M1ThresholdEventA2-ExtIEs X2AP-PROTOCOL-EXTENSION ::= {
    ...
}

M3Configuration ::= SEQUENCE {
    m3period            M3period,
    iE-Extensions       ProtocolExtensionContainer { {M3Configuration-ExtIEs} } OPTIONAL,
    ...
}

M3Configuration-ExtIEs X2AP-PROTOCOL-EXTENSION ::= {
    ...
}

M3period ::= ENUMERATED {ms100, ms1000, ms10000, ... }

M4Configuration ::= SEQUENCE {
    m4period            M4period,
    m4-links-to-log     Links-to-log,
    iE-Extensions       ProtocolExtensionContainer { {M4Configuration-ExtIEs} } OPTIONAL,
    ...
}

M4Configuration-ExtIEs X2AP-PROTOCOL-EXTENSION ::= {
{ ID id-M4ReportAmount      CRITICALITY ignore  EXTENSION M4ReportAmountMDT     PRESENCE optional},

    ...
}

M4period ::= ENUMERATED {ms1024, ms2048, ms5120, ms10240, min1, ... }

M4ReportAmountMDT ::= ENUMERATED {r1, r2, r4, r8, r16, r32, r64, infinity, ...}

M5Configuration ::= SEQUENCE {
    m5period            M5period,
    m5-links-to-log     Links-to-log,
    iE-Extensions       ProtocolExtensionContainer { {M5Configuration-ExtIEs} } OPTIONAL,
    ...
}

M5Configuration-ExtIEs X2AP-PROTOCOL-EXTENSION ::= {
{ ID id-M5ReportAmount      CRITICALITY ignore  EXTENSION M5ReportAmountMDT     PRESENCE optional   },

    ...
}

M5period ::= ENUMERATED {ms1024, ms2048, ms5120, ms10240, min1, ... }

M5ReportAmountMDT ::= ENUMERATED {r1, r2, r4, r8, r16, r32, r64, infinity, ...}

M6Configuration ::= SEQUENCE {
    m6report-interval   M6report-interval,
    m6delay-threshold   M6delay-threshold   OPTIONAL,
-- This IE shall be present if the M6 Links to log IE is set to “uplink” or to “both-uplink-and-downlink” --
    m6-links-to-log     Links-to-log,
    iE-Extensions       ProtocolExtensionContainer { {M6Configuration-ExtIEs} } OPTIONAL,
    ...
}

M6Configuration-ExtIEs X2AP-PROTOCOL-EXTENSION ::= {
{ ID id-M6ReportAmount      CRITICALITY ignore  EXTENSION M6ReportAmountMDT     PRESENCE optional   },

    ...
}

M6report-interval ::= ENUMERATED { ms1024, ms2048, ms5120, ms10240, ... }

M6delay-threshold ::= ENUMERATED { ms30, ms40, ms50, ms60, ms70, ms80, ms90, ms100, ms150, ms300, ms500, ms750, ... }

M6ReportAmountMDT ::= ENUMERATED {r1, r2, r4, r8, r16, r32, r64, infinity, ...}

M7Configuration ::= SEQUENCE {
    m7period            M7period,
    m7-links-to-log     Links-to-log,
    iE-Extensions       ProtocolExtensionContainer { {M7Configuration-ExtIEs} } OPTIONAL,
    ...
}

M7Configuration-ExtIEs X2AP-PROTOCOL-EXTENSION ::= {
{ ID id-M7ReportAmount      CRITICALITY ignore  EXTENSION M7ReportAmountMDT     PRESENCE optional   },

    ...
}

M7period ::= INTEGER(1..60, ...)

M7ReportAmountMDT ::= ENUMERATED {r1, r2, r4, r8, r16, r32, r64, infinity, ...}

MakeBeforeBreakIndicator::= ENUMERATED {true, ...}

ManagementBasedMDTallowed ::= ENUMERATED {allowed, ...}

Masked-IMEISV ::= BIT STRING (SIZE (64))

MaxCHOpreparations ::= INTEGER(1..8, ...)

MDT-Activation      ::= ENUMERATED {
    immediate-MDT-only,
    immediate-MDT-and-Trace,
    ...
}

MDT-Configuration ::= SEQUENCE {
    mdt-Activation              MDT-Activation,
    areaScopeOfMDT              AreaScopeOfMDT,
    measurementsToActivate      MeasurementsToActivate,
    m1reportingTrigger          M1ReportingTrigger,
    m1thresholdeventA2          M1ThresholdEventA2          OPTIONAL,
-- Included in case of event-triggered, or event-triggered periodic reporting for measurement M1
    m1periodicReporting         M1PeriodicReporting         OPTIONAL,
-- Included in case of periodic, or event-triggered periodic reporting for measurement M1
    iE-Extensions               ProtocolExtensionContainer { {MDT-Configuration-ExtIEs} } OPTIONAL,
    ...
}

MDT-Configuration-ExtIEs X2AP-PROTOCOL-EXTENSION ::= {
    {ID id-M3Configuration                          CRITICALITY ignore  EXTENSION M3Configuration                               PRESENCE conditional}|
    {ID id-M4Configuration                          CRITICALITY ignore  EXTENSION M4Configuration                               PRESENCE conditional}|
    {ID id-M5Configuration                          CRITICALITY ignore  EXTENSION M5Configuration                               PRESENCE conditional}|
    {ID id-MDT-Location-Info                        CRITICALITY ignore  EXTENSION MDT-Location-Info                         PRESENCE optional}|
    {ID id-SignallingBasedMDTPLMNList               CRITICALITY ignore  EXTENSION MDTPLMNList                                   PRESENCE optional}|
    {ID id-M6Configuration                          CRITICALITY ignore  EXTENSION M6Configuration                               PRESENCE conditional}|
    {ID id-M7Configuration                          CRITICALITY ignore  EXTENSION M7Configuration                               PRESENCE conditional}|
    { ID id-BluetoothMeasurementConfiguration       CRITICALITY ignore  EXTENSION BluetoothMeasurementConfiguration     PRESENCE optional}|
    { ID id-WLANMeasurementConfiguration            CRITICALITY ignore  EXTENSION WLANMeasurementConfiguration          PRESENCE optional}|
    { ID id-SensorMeasurementConfiguration          CRITICALITY ignore  EXTENSION SensorMeasurementConfiguration        PRESENCE optional},
    ...
}

MDTPLMNList ::= SEQUENCE (SIZE(1..maxnoofMDTPLMNs)) OF PLMN-Identity

MDT-Location-Info ::= BIT STRING (SIZE (8))

Measurement-ID  ::= INTEGER (1..4095, ...)

Measurement-ID-ENDC ::= INTEGER (1..4095, ...)


MeasurementsToActivate::= BIT STRING (SIZE (8))

MeasurementThresholdA2 ::= CHOICE {
    threshold-RSRP              Threshold-RSRP,
    threshold-RSRQ              Threshold-RSRQ,
    ...
}

MeNBCoordinationAssistanceInformation ::= ENUMERATED{
    coordination-not-required,
    ...
}

MeNBResourceCoordinationInformation ::= SEQUENCE {
    eUTRA-Cell-ID                   ECGI,
    uLCoordinationInformation       BIT STRING (SIZE(6..4400, ...)),
    dLCoordinationInformation       BIT STRING (SIZE(6..4400, ...))     OPTIONAL,
    iE-Extensions                   ProtocolExtensionContainer { {MeNBResourceCoordinationInformationExtIEs} }       OPTIONAL,
    ...
}

MeNBResourceCoordinationInformationExtIEs X2AP-PROTOCOL-EXTENSION ::= {
    { ID id-NRCGI                                   CRITICALITY ignore  EXTENSION NRCGI                                             PRESENCE optional}|
    { ID id-MeNBCoordinationAssistanceInformation       CRITICALITY reject  EXTENSION MeNBCoordinationAssistanceInformation PRESENCE optional},
    ...
}

MeNBtoSeNBContainer ::= OCTET STRING

MME-Group-ID    ::= OCTET STRING (SIZE (2))

MME-Code        ::= OCTET STRING (SIZE (1))

MBMS-Service-Area-Identity-List ::= SEQUENCE (SIZE(1.. maxnoofMBMSServiceAreaIdentities)) OF MBMS-Service-Area-Identity

MBMS-Service-Area-Identity ::= OCTET STRING (SIZE (2))

MBSFN-Subframe-Infolist::= SEQUENCE (SIZE(1.. maxnoofMBSFN)) OF MBSFN-Subframe-Info

MBSFN-Subframe-Info ::= SEQUENCE {
    radioframeAllocationPeriod      RadioframeAllocationPeriod,
    radioframeAllocationOffset      RadioframeAllocationOffset,
    subframeAllocation              SubframeAllocation,
    iE-Extensions                   ProtocolExtensionContainer { {MBSFN-Subframe-Info-ExtIEs} }     OPTIONAL,
    ...
}

MBSFN-Subframe-Info-ExtIEs X2AP-PROTOCOL-EXTENSION ::= {
    ...
}

MDT-ConfigurationNR ::= OCTET STRING

MobilityParametersModificationRange ::= SEQUENCE {
    handoverTriggerChangeLowerLimit     INTEGER (-20..20),
    handoverTriggerChangeUpperLimit     INTEGER (-20..20),
    ...
}

MobilityParametersInformation ::= SEQUENCE {
    handoverTriggerChange           INTEGER (-20..20),
    ...
}

MultibandInfoList ::= SEQUENCE (SIZE(1..maxnoofBands)) OF BandInfo

MessageOversizeNotification ::= SEQUENCE {
    maximumCellListSize                             MaximumCellListSize,
    iE-Extensions                   ProtocolExtensionContainer { {MessageOversizeNotification-ExtIEs} }     OPTIONAL,
    ...
}

MessageOversizeNotification-ExtIEs X2AP-PROTOCOL-EXTENSION ::= {
    ...
}

MaximumCellListSize ::= INTEGER(1..16384, ...)

BandInfo    ::= SEQUENCE {
    freqBandIndicator       FreqBandIndicator,
    iE-Extensions           ProtocolExtensionContainer { {BandInfo-ExtIEs} }    OPTIONAL,
    ...
}

BandInfo-ExtIEs X2AP-PROTOCOL-EXTENSION ::= {
    ...
}

MeNBtoSgNBContainer ::= OCTET STRING

SplitSRBs ::= ENUMERATED {srb1, srb2, srb1and2, ...}

SplitSRB ::= SEQUENCE {
    rrcContainer                RRCContainer            OPTIONAL,
    srbType                     SRBType,
    deliveryStatus              DeliveryStatus          OPTIONAL,
    iE-Extensions               ProtocolExtensionContainer { {SplitSRB-ExtIEs} } OPTIONAL,
    ...
}

SplitSRB-ExtIEs X2AP-PROTOCOL-EXTENSION ::= {
    ...
}

-- N

NBIoT-UL-DL-AlignmentOffset ::= ENUMERATED {
    khz-7dot5,
    khz0,
    khz7dot5,
    ...
}

NBIoT-RLF-Report-Container ::= OCTET STRING

Neighbour-Information ::= SEQUENCE (SIZE (0..maxnoofNeighbours)) OF SEQUENCE {
    eCGI                        ECGI,
    pCI                         PCI,
    eARFCN                      EARFCN,
    iE-Extensions               ProtocolExtensionContainer { {Neighbour-Information-ExtIEs} } OPTIONAL,
    ...
}

Neighbour-Information-ExtIEs X2AP-PROTOCOL-EXTENSION ::= {
    { ID id-NeighbourTAC        CRITICALITY ignore  EXTENSION TAC               PRESENCE optional}|
    { ID id-eARFCNExtension     CRITICALITY reject  EXTENSION EARFCNExtension   PRESENCE optional},
    ...
}

NextHopChainingCount ::= INTEGER (0..7)

NewDRBIDrequest::= ENUMERATED {true, ...}

Number-of-Antennaports ::= ENUMERATED {
        an1,
        an2,
        an4,
        ...
}

NRCapacityValue                 ::= SEQUENCE {
    capacityValue                       INTEGER (0..100),
    ssbAreaCapacityValue-List           SSBAreaCapacityValue-List                           OPTIONAL,
    iE-Extensions                       ProtocolExtensionContainer { { NRCapacityValue-ExtIEs} } OPTIONAL,
    ...
}

NRCapacityValue-ExtIEs X2AP-PROTOCOL-EXTENSION ::= {
    ...
}

NRCarrierList ::= SEQUENCE (SIZE(1..maxnoofNRSCSs)) OF NRCarrierItem

NRCarrierItem ::= SEQUENCE {
    carrierSCS                  NRSCS,
    offsetToCarrier             INTEGER (0..2199, ...),
    carrierBandwidth            INTEGER (0..maxnoofNRPhysicalResourceBlocks, ...),
    iE-Extension        ProtocolExtensionContainer { {NRCarrierItem-ExtIEs} }       OPTIONAL,
    ...
}

NRCarrierItem-ExtIEs X2AP-PROTOCOL-EXTENSION ::= {
    ...
}

NRCellCapacityClassValue ::= INTEGER (1..100, ...)

NRCellPRACHConfig ::= OCTET STRING

NRCompositeAvailableCapacityGroup   ::= SEQUENCE {
    compositeAvailableCapacityDL        NRCompositeAvailableCapacity,
    compositeAvailableCapacityUL        NRCompositeAvailableCapacity,
    iE-Extensions                       ProtocolExtensionContainer { {NRCompositeAvailableCapacityGroup-ExtIEs} } OPTIONAL,
    ...
}

NRCompositeAvailableCapacityGroup-ExtIEs X2AP-PROTOCOL-EXTENSION ::= {
    ...
}

NRCompositeAvailableCapacity ::= SEQUENCE {
    cellCapacityClassValue              NRCellCapacityClassValue                            OPTIONAL,
    capacityValue                       NRCapacityValue,
    iE-Extensions                       ProtocolExtensionContainer { {NRCompositeAvailableCapacity-ExtIEs} } OPTIONAL,
    ...
}

NRCompositeAvailableCapacity-ExtIEs X2AP-PROTOCOL-EXTENSION ::= {
    ...
}

NRFreqInfo ::= SEQUENCE{
    nRARFCN         INTEGER (0.. 3279165),
    freqBandListNr  SEQUENCE (SIZE(1..maxnoofNrCellBands)) OF FreqBandNrItem,
    sULInformation  SULInformation      OPTIONAL,
    iE-Extensions   ProtocolExtensionContainer { {NRFreqInfo-ExtIEs} } OPTIONAL,

    ...
}

NRFreqInfo-ExtIEs X2AP-PROTOCOL-EXTENSION ::= {
    { ID id-FrequencyShift7p5khz            CRITICALITY ignore  EXTENSION FrequencyShift7p5khz  PRESENCE optional},
    ...
}

NRCellIdentifier ::= BIT STRING (SIZE (36))

NRCGI ::= SEQUENCE {
    pLMN-Identity               PLMN-Identity,
    nRcellIdentifier                NRCellIdentifier,
    iE-Extensions               ProtocolExtensionContainer { {NRCGI-ExtIEs} } OPTIONAL,
    ...
}

NRCGI-ExtIEs X2AP-PROTOCOL-EXTENSION ::= {
    ...
}

NRRAReportContainer ::= OCTET STRING

NRRAReport  ::= SEQUENCE (SIZE(1.. maxnoofRAReports)) OF NRRAReportList-Item

NRRAReportList-Item ::= SEQUENCE {
    nRRAReport                      NRRAReportContainer,
    uEAssitantIdentifier                SgNB-UE-X2AP-ID                                                     OPTIONAL,
    iE-Extensions                       ProtocolExtensionContainer { { NRRAReportList-Item-ExtIEs} }    OPTIONAL,
    ...
}

NRRAReportList-Item-ExtIEs X2AP-PROTOCOL-EXTENSION ::= {
{ ID id-PSCellListContainer     CRITICALITY ignore  EXTENSION PSCellListContainer   PRESENCE optional},
    ...
}

NRNeighbour-Information ::= SEQUENCE (SIZE (1.. maxofNRNeighbours))OF SEQUENCE {
    nrpCI                           NRPCI,
    nrCellID                        NRCGI,
    fiveGS-TAC                      FiveGS-TAC  OPTIONAL,
    configured-TAC                  TAC         OPTIONAL,
    measurementTimingConfiguration  OCTET STRING,
    nRNeighbourModeInfo             CHOICE {
        fdd     FDD-InfoNeighbourServedNRCell-Information,
        tdd     TDD-InfoNeighbourServedNRCell-Information,
        ...
    },
    iE-Extensions                       ProtocolExtensionContainer { {NRNeighbour-Information-ExtIEs} } OPTIONAL,
    ...
}

NRNeighbour-Information-ExtIEs X2AP-PROTOCOL-EXTENSION ::= {
    {ID id-CSI-RSTransmissionIndication     CRITICALITY ignore  EXTENSION CSI-RSTransmissionIndication  PRESENCE optional}|
    {ID id-SSB-PositionsInBurst             CRITICALITY ignore  EXTENSION SSB-PositionsInBurst                  PRESENCE optional}|
    {ID id-NRCellPRACHConfig                CRITICALITY ignore  EXTENSION NRCellPRACHConfig                     PRESENCE optional}|
    {ID id-Additional-Measurement-Timing-Configuration-List     CRITICALITY ignore  EXTENSION Additional-Measurement-Timing-Configuration-List      PRESENCE optional },
    ...
}

NPRACHConfiguration::= SEQUENCE {
    fdd-or-tdd              CHOICE {
        fdd         NPRACHConfiguration-FDD,
        tdd         NPRACHConfiguration-TDD,
        ...
    },  iE-Extensions                       ProtocolExtensionContainer { { NPRACHConfiguration-ExtIEs} }    OPTIONAL,
...
}

NPRACHConfiguration-ExtIEs X2AP-PROTOCOL-EXTENSION ::= {
    ...
}

NPRACHConfiguration-FDD::= SEQUENCE {
    nprach-CP-length                        NPRACH-CP-Length,
    anchorCarrier-NPRACHConfig                      OCTET STRING,
    anchorCarrier-EDT-NPRACHConfig                  OCTET STRING                        OPTIONAL,
    anchorCarrier-Format2-NPRACHConfig              OCTET STRING                        OPTIONAL,
    anchorCarrier-Format2-EDT-NPRACHConfig          OCTET STRING                        OPTIONAL,
    non-anchorCarrier-NPRACHConfig                  OCTET STRING                        OPTIONAL,
    non-anchorCarrier-Format2-NPRACHConfig          OCTET STRING                        OPTIONAL,
    iE-Extensions       ProtocolExtensionContainer { { NPRACHConfiguration-FDD-ExtIEs} }    OPTIONAL,

...
}

NPRACHConfiguration-FDD-ExtIEs X2AP-PROTOCOL-EXTENSION ::= {
    ...
}

NPRACHConfiguration-TDD::= SEQUENCE {
    nprach-preambleFormat                           NPRACH-preambleFormat,
    anchorCarrier-NPRACHConfigTDD                   OCTET STRING,
    non-anchorCarrierFequencyConfiglist             Non-AnchorCarrierFrequencylist      OPTIONAL,
    non-anchorCarrier-NPRACHConfigTDD               OCTET STRING                        OPTIONAL,
    iE-Extensions       ProtocolExtensionContainer { { NPRACHConfiguration-TDD-ExtIEs} }    OPTIONAL,

...
}

NPRACHConfiguration-TDD-ExtIEs X2AP-PROTOCOL-EXTENSION ::= {
    ...
}

NPRACH-CP-Length::=     ENUMERATED {
    us66dot7,
    us266dot7,
    ...
}

NPRACH-preambleFormat::=    ENUMERATED {fmt0,fmt1,fmt2,fmt0a,fmt1a,...}

Non-AnchorCarrierFrequencylist ::= SEQUENCE (SIZE(1..maxnoofNonAnchorCarrierFreqConfig)) OF
    SEQUENCE {
        non-anchorCarrioerFrquency      OCTET STRING,
        iE-Extensions                   ProtocolExtensionContainer { { Non-AnchorCarrierFrequencylist-ExtIEs} } OPTIONAL,
        ...
    }

Non-AnchorCarrierFrequencylist-ExtIEs X2AP-PROTOCOL-EXTENSION ::= {
    ...
}


NRPCI ::= INTEGER (0..1007)

NRrestrictioninEPSasSecondaryRAT ::= ENUMERATED {
    nRrestrictedinEPSasSecondaryRAT,
    ...
}

MeasurementResultforNRCellsPossiblyAggregated ::= SEQUENCE (SIZE(1.. maxnoofReportedNRCellsPossiblyAggregated)) OF MeasurementResultforNRCellsPossiblyAggregated-Item

MeasurementResultforNRCellsPossiblyAggregated-Item ::= SEQUENCE {
    cellID                                      NRCGI,
    nrCompositeAvailableCapacityGroup           NRCompositeAvailableCapacityGroup           OPTIONAL,
    iE-Extension        ProtocolExtensionContainer { { MeasurementResultforNRCellsPossiblyAggregated-Item-ExtIEs} } OPTIONAL,
    ...
}

MeasurementResultforNRCellsPossiblyAggregated-Item-ExtIEs X2AP-PROTOCOL-EXTENSION ::= {
    ...
}

NRRadioResourceStatus   ::= SEQUENCE {
    ssbAreaRadioResourceStatus-List     SSBAreaRadioResourceStatus-List,
    iE-Extensions                       ProtocolExtensionContainer { {NRRadioResourceStatus-ExtIEs} } OPTIONAL,
    ...
}

NRRadioResourceStatus-ExtIEs X2AP-PROTOCOL-EXTENSION ::= {
    { ID id-MIMOPRBusageInformation         CRITICALITY ignore  EXTENSION MIMOPRBusageInformation           PRESENCE optional   },
    ...
}

MIMOPRBusageInformation ::= SEQUENCE {
    dl-GBR-PRB-usage-for-MIMO                   DL-GBR-PRB-usage-for-MIMO,
    ul-GBR-PRB-usage-for-MIMO                   UL-GBR-PRB-usage-for-MIMO,
    dl-non-GBR-PRB-usage-for-MIMO               DL-non-GBR-PRB-usage-for-MIMO,
    ul-non-GBR-PRB-usage-for-MIMO               UL-non-GBR-PRB-usage-for-MIMO,
    dl-Total-PRB-usage-for-MIMO                 DL-Total-PRB-usage-for-MIMO,
    ul-Total-PRB-usage-for-MIMO                 UL-Total-PRB-usage-for-MIMO,
    iE-Extensions                           ProtocolExtensionContainer { { MIMOPRBusageInformation-ExtIEs} }    OPTIONAL,
    ...
}

MIMOPRBusageInformation-ExtIEs X2AP-PROTOCOL-EXTENSION ::= {
    ...
}

NRrestrictionin5GS ::= ENUMERATED {
    nRrestrictedin5GS,
    ...
}

NRencryptionAlgorithms ::= BIT STRING (SIZE (16,...))
NRintegrityProtectionAlgorithms ::= BIT STRING (SIZE (16,...))

NR-TxBW ::= SEQUENCE {
    nRSCS   NRSCS,
    nRNRB   NRNRB,
    iE-Extensions               ProtocolExtensionContainer { {NR-TxBW-ExtIEs} } OPTIONAL,
    ...
}

NR-TxBW-ExtIEs X2AP-PROTOCOL-EXTENSION ::= {
    ...
}

NRNRB ::= ENUMERATED { nrb11, nrb18, nrb24, nrb25, nrb31, nrb32, nrb38, nrb51, nrb52, nrb65, nrb66, nrb78, nrb79, nrb93, nrb106, nrb107, nrb121, nrb132, nrb133, nrb135, nrb160, nrb162, nrb189, nrb216, nrb217, nrb245, nrb264, nrb270, nrb273, ... , nrb44, nrb58, nrb92, nrb119, nrb188, nrb242}

NRSCS ::= ENUMERATED { scs15, scs30, scs60, scs120, ...}

NRS-NSSS-PowerOffset ::= ENUMERATED { minusThree, zero, three, ...}

FiveGS-TAC ::= OCTET STRING (SIZE (3))

NRUeReport ::= SEQUENCE {
    uENRMeasurements            RRCContainer,
    iE-Extensions           ProtocolExtensionContainer { { NRUeReport-ExtIEs} } OPTIONAL,
    ...
}

NRUeReport-ExtIEs X2AP-PROTOCOL-EXTENSION ::= {
    ...
}

NRUESidelinkAggregateMaximumBitRate ::= SEQUENCE {
    uESidelinkAggregateMaximumBitRate       BitRate,
    iE-Extensions                   ProtocolExtensionContainer { { NRUESidelinkAggregateMaximumBitRate-ExtIEs} } OPTIONAL,
    ...
}

NRUESidelinkAggregateMaximumBitRate-ExtIEs X2AP-PROTOCOL-EXTENSION ::= {
    ...
}

NRUESecurityCapabilities ::= SEQUENCE {
    nRencryptionAlgorithms              NRencryptionAlgorithms,
    nRintegrityProtectionAlgorithms     NRintegrityProtectionAlgorithms,
    iE-Extensions                       ProtocolExtensionContainer { {NRUESecurityCapabilities-ExtIEs} }    OPTIONAL,
...
}

NRUESecurityCapabilities-ExtIEs X2AP-PROTOCOL-EXTENSION ::= {
    ...
}

NSSS-NumOccasionDifferentPrecoder ::= ENUMERATED { two, four, eight, ...}

NRV2XServicesAuthorized ::= SEQUENCE {
    vehicleUE           VehicleUE                                                       OPTIONAL,
    pedestrianUE        PedestrianUE                                                    OPTIONAL,
    iE-Extensions       ProtocolExtensionContainer { {NRV2XServicesAuthorized-ExtIEs} } OPTIONAL,
    ...
}

NRV2XServicesAuthorized-ExtIEs X2AP-PROTOCOL-EXTENSION ::= {
    ...
}

-- O

OffsetOfNbiotChannelNumberToEARFCN ::= ENUMERATED {
        minusTen,
        minusNine,
        minusEight,
        minusSeven,
        minusSix,
        minusFive,
        minusFour,
        minusThree,
        minusTwo,
        minusOne,
        minusZeroDotFive,
        zero,
        one,
        two,
        three,
        four,
        five,
        six,
        seven,
        eight,
        nine,
        ...,
        minusEightDotFive,
        minusFourDotFive,
        threeDotFive,
        sevenDotFive
}

Oneframe ::= BIT STRING (SIZE (6))

-- P

Packet-LossRate ::= INTEGER(0..1000)

PA-Values ::= ENUMERATED {
    dB-6,
    dB-4dot77,
    dB-3,
    dB-1dot77,
    dB0,
    dB1,
    dB2,
    dB3,
    ...
}

PC5QoSParameters ::= SEQUENCE {
    pc5QoSFlowList              PC5QoSFlowList,
    pc5LinkAggregatedBitRates   BitRate             OPTIONAL,
    iE-Extensions       ProtocolExtensionContainer { { PC5QoSParameters-ExtIEs} }   OPTIONAL,
    ...
}

PC5QoSParameters-ExtIEs X2AP-PROTOCOL-EXTENSION ::= {
    ...
}

PC5QoSFlowList ::= SEQUENCE (SIZE(1..maxnoofPC5QoSFlows)) OF PC5QoSFlowItem

PC5QoSFlowItem::= SEQUENCE {
    pQI                         FiveQI,
    pc5FlowBitRates             PC5FlowBitRates             OPTIONAL,
    range                       Range                       OPTIONAL,
    iE-Extensions       ProtocolExtensionContainer { { PC5QoSFlowItem-ExtIEs} } OPTIONAL,
    ...
}

PC5QoSFlowItem-ExtIEs X2AP-PROTOCOL-EXTENSION ::= {
    ...
}

PC5FlowBitRates ::= SEQUENCE {
    guaranteedFlowBitRate       BitRate,
    maximumFlowBitRate      BitRate,
    iE-Extensions       ProtocolExtensionContainer { { PC5FlowBitRates-ExtIEs} }    OPTIONAL,
    ...
}

PC5FlowBitRates-ExtIEs X2AP-PROTOCOL-EXTENSION ::= {
    ...
}

PDCPChangeIndication ::= ENUMERATED {s-KgNB-update-required, pDCP-data-recovery-required,...}

PDCP-SN ::= INTEGER (0..4095)

PDCP-SNExtended ::= INTEGER (0..32767)

PDCP-SNlength18 ::= INTEGER (0..262143)

PDCPSnLength    ::= ENUMERATED {twelve-bits,eighteen-bits,...}

PCI ::= INTEGER (0..503, ...)

PLMN-Identity ::= OCTET STRING (SIZE(3))

Port-Number ::= OCTET STRING (SIZE (2))

PRACH-Configuration ::= SEQUENCE {
    rootSequenceIndex                       INTEGER (0..837),
    zeroCorrelationIndex                    INTEGER (0..15),
    highSpeedFlag                           BOOLEAN,
    prach-FreqOffset                        INTEGER (0..94),
    prach-ConfigIndex                       INTEGER (0..63)     OPTIONAL, -- present for TDD --
    iE-Extensions                           ProtocolExtensionContainer { {PRACH-Configuration-ExtIEs} } OPTIONAL,
    ...
}

PLMNAreaBasedQMC ::= SEQUENCE {
    plmnListforQMC      PLMNListforQMC,
    iE-Extensions       ProtocolExtensionContainer { {PLMNAreaBasedQMC-ExtIEs} } OPTIONAL,
    ...
}

PLMNAreaBasedQMC-ExtIEs X2AP-PROTOCOL-EXTENSION ::= {
    ...
}

PLMNListforQMC ::= SEQUENCE (SIZE(1..maxnoofPLMNforQMC)) OF PLMN-Identity


PRACH-Configuration-ExtIEs X2AP-PROTOCOL-EXTENSION ::= {
    ...
}

Pre-emptionCapability ::= ENUMERATED {
    shall-not-trigger-pre-emption,
    may-trigger-pre-emption
}

Pre-emptionVulnerability ::= ENUMERATED {
    not-pre-emptable,
    pre-emptable
}

PriorityLevel               ::= INTEGER { spare (0), highest (1), lowest (14), no-priority (15) } (0..15)

ProSeAuthorized ::= SEQUENCE {
    proSeDirectDiscovery        ProSeDirectDiscovery            OPTIONAL,
    proSeDirectCommunication    ProSeDirectCommunication        OPTIONAL,
    iE-Extensions               ProtocolExtensionContainer { {ProSeAuthorized-ExtIEs} } OPTIONAL,
    ...
}

ProSeAuthorized-ExtIEs X2AP-PROTOCOL-EXTENSION ::= {
    { ID id-ProSeUEtoNetworkRelaying    CRITICALITY ignore  EXTENSION ProSeUEtoNetworkRelaying      PRESENCE optional},
    ...
}

ProSeDirectDiscovery ::= ENUMERATED {
    authorized,
    not-authorized,
    ...
}

ProSeDirectCommunication ::= ENUMERATED {
    authorized,
    not-authorized,
    ...
}

ProSeUEtoNetworkRelaying ::= ENUMERATED {
    authorized,
    not-authorized,
    ...
}

ProtectedEUTRAResourceIndication::= SEQUENCE {
    activationSFN                           INTEGER (0..1023),
    protectedResourceList                   ProtectedResourceList,
    mBSFNControlRegionLength                INTEGER (0..3) OPTIONAL,
    pDCCHRegionLength                       INTEGER (1..3) OPTIONAL,
    iE-Extensions                           ProtocolExtensionContainer { {ProtectedEUTRAResourceIndication-ExtIEs} }    OPTIONAL,
    ...
}

ProtectedEUTRAResourceIndication-ExtIEs X2AP-PROTOCOL-EXTENSION ::= {
    ...
} -- Rapporteur: missing extension --


ProtectedFootprintTimePattern ::= SEQUENCE {
    protectedFootprintTimePeriodicity               INTEGER (1..320, ...),
    protectedFootprintStartTime                     INTEGER (1..20, ...),
    iE-Extensions                                   ProtocolExtensionContainer { {ProtectedFootprintTimePattern-ExtIEs} }   OPTIONAL,
    ...
}

ProtectedFootprintTimePattern-ExtIEs X2AP-PROTOCOL-EXTENSION ::= {
    ...
}

ProtectedResourceList ::= SEQUENCE (SIZE(1.. maxnoofProtectedResourcePatterns)) OF ProtectedResourceList-Item

ProtectedResourceList-Item ::= SEQUENCE {
    resourceType                    ResourceType,
    intraPRBProtectedResourceFootprint      BIT STRING (SIZE(84, ...)),
    protectedFootprintFrequencyPattern      BIT STRING (SIZE(6..110, ...)),
    protectedFootprintTimePattern           ProtectedFootprintTimePattern,
    iE-Extensions                           ProtocolExtensionContainer { {ProtectedResourceList-Item-ExtIEs} }  OPTIONAL,
    ...
}

ProtectedResourceList-Item-ExtIEs X2AP-PROTOCOL-EXTENSION ::= {
    ...
}

PartialListIndicator ::= ENUMERATED {partial, ...}

PrivacyIndicator ::= ENUMERATED {
    immediate-MDT,
    logged-MDT,
    ...
}

PSCellHistoryInformationRetrieve ::= ENUMERATED {query, ...}

PSCell-UE-HistoryInformation ::= SEQUENCE (SIZE(1.. maxnoofPSCellsPerPrimaryCellinUEHistoryInfo)) OF LastVisitedPSCell-Item

PSCellChangeHistory ::= ENUMERATED {reportingFullHistory,...}

PSCellListContainer ::= OCTET STRING


-- Q

QCI ::= INTEGER (0..255)

QoS-Mapping-Information ::= SEQUENCE {
dscp                            BIT STRING (SIZE(6))            OPTIONAL,
flow-label                      BIT STRING (SIZE(20))       OPTIONAL,
iE-Extensions                   ProtocolExtensionContainer { {QoS-Mapping-Information-ExtIEs} } OPTIONAL,
...
}

QoS-Mapping-Information-ExtIEs X2AP-PROTOCOL-EXTENSION ::= {
    ...
}

-- R

RadioframeAllocationOffset ::= INTEGER (0..7, ...)

RadioframeAllocationPeriod ::= ENUMERATED{
    n1,
    n2,
    n4,
    n8,
    n16,
    n32,
    ...
}


RadioResourceStatus ::= SEQUENCE {
    dL-GBR-PRB-usage                            DL-GBR-PRB-usage,
    uL-GBR-PRB-usage                            UL-GBR-PRB-usage,
    dL-non-GBR-PRB-usage                        DL-non-GBR-PRB-usage,
    uL-non-GBR-PRB-usage                        UL-non-GBR-PRB-usage,
    dL-Total-PRB-usage                          DL-Total-PRB-usage,
    uL-Total-PRB-usage                          UL-Total-PRB-usage,
    iE-Extensions                               ProtocolExtensionContainer { {RadioResourceStatus-ExtIEs} } OPTIONAL,
    ...
}

RadioResourceStatus-ExtIEs X2AP-PROTOCOL-EXTENSION ::= {
    {ID id-DL-scheduling-PDCCH-CCE-usage        CRITICALITY ignore  EXTENSION DL-scheduling-PDCCH-CCE-usage     PRESENCE optional}|
    {ID id-UL-scheduling-PDCCH-CCE-usage        CRITICALITY ignore  EXTENSION UL-scheduling-PDCCH-CCE-usage     PRESENCE optional},
    ...
}

Range ::= ENUMERATED {m50, m80, m180, m200, m350, m400, m500, m700, m1000, ...}

RAN-UE-NGAP-ID ::= INTEGER (0..4294967295)

RAT-Restrictions ::= SEQUENCE (SIZE(1..maxnoofEPLMNsPlusOne)) OF RAT-RestrictionsItem

RAT-RestrictionsItem ::= SEQUENCE {
    pLMN-Identity                   PLMN-Identity,
    rAT-RestrictionInformation      BIT STRING (SIZE(8, ...)),
    iE-Extensions                   ProtocolExtensionContainer { { RAT-RestrictionsItem-ExtIEs} }   OPTIONAL,
    ...
}

RAT-RestrictionsItem-ExtIEs     X2AP-PROTOCOL-EXTENSION ::= {
    ...
}

ReceiveStatusofULPDCPSDUs ::= BIT STRING (SIZE(4096))

ReceiveStatusOfULPDCPSDUsExtended ::= BIT STRING (SIZE(1..16384))

ReceiveStatusOfULPDCPSDUsPDCP-SNlength18 ::= BIT STRING (SIZE(1..131072))

ReleaseFastMCGRecoveryViaSRB3 ::= ENUMERATED {true,...}

Reestablishment-Indication ::= ENUMERATED {
    reestablished,
    ...
}

Registration-Request    ::= ENUMERATED {
    start,
    stop,
    ...,
    partial-stop,
    add
}

Registration-Request-ENDC   ::= ENUMERATED {
    start,
    stop,
    add,
    ...
}


RelativeNarrowbandTxPower ::= SEQUENCE {

    rNTP-PerPRB                         BIT STRING (SIZE(6..110, ...)),
    rNTP-Threshold                      RNTP-Threshold,
    numberOfCellSpecificAntennaPorts    ENUMERATED {one, two, four, ...},
    p-B                                 INTEGER (0..3,...),
    pDCCH-InterferenceImpact            INTEGER (0..4,...),
    iE-Extensions                       ProtocolExtensionContainer { {RelativeNarrowbandTxPower-ExtIEs} } OPTIONAL,
    ...
}

RelativeNarrowbandTxPower-ExtIEs X2AP-PROTOCOL-EXTENSION ::= {
    { ID id-enhancedRNTP    CRITICALITY ignore  EXTENSION EnhancedRNTP      PRESENCE optional },
    ...
}

ReplacingCellsList ::= SEQUENCE (SIZE(0.. maxCellineNB)) OF ReplacingCellsList-Item

ReplacingCellsList-Item ::= SEQUENCE {
    eCGI            ECGI,
    ...
}

ReportAmountMDT ::= ENUMERATED{r1, r2, r4, r8, r16, r32, r64, rinfinity}

ReportArea ::= ENUMERATED{
    ecgi,
    ...
}

ReportCharacteristics   ::= BIT STRING (SIZE (32))

ReportingPeriodicityCSIR ::= ENUMERATED {
    ms5,
    ms10,
    ms20,
    ms40,
    ms80,
...
}

ReportCharacteristics-ENDC  ::= BIT STRING (SIZE (32))

ReportingPeriodicityRSRPMR ::= ENUMERATED {
    one-hundred-20-ms,
    two-hundred-40-ms,
    four-hundred-80-ms,
    six-hundred-40-ms,
...
}

ReportIntervalMDT ::= ENUMERATED {ms120, ms240, ms480, ms640, ms1024, ms2048, ms5120, ms10240, min1, min6, min12, min30, min60}

RequestedFastMCGRecoveryViaSRB3 ::= ENUMERATED {true,...}

RequestedFastMCGRecoveryViaSRB3Release ::= ENUMERATED {true,...}

ReservedSubframePattern ::= SEQUENCE{
    subframeType                    SubframeType,
    reservedSubframePattern         BIT STRING (SIZE(10..160)),
    mBSFNControlRegionLength        INTEGER (0..3),
    iE-Extensions                   ProtocolExtensionContainer { {ReservedSubframePattern-ExtIEs} } OPTIONAL,
    ...
}

ReservedSubframePattern-ExtIEs X2AP-PROTOCOL-EXTENSION ::= {
    ...
}

ResourceType ::= ENUMERATED {
    downlinknonCRS,
    cRS,
    uplink,
    ...
}

ResumeID    ::= CHOICE {
    non-truncated   BIT STRING(SIZE(40)),
    truncated       BIT STRING(SIZE(24)),
    ...
}

RLCMode ::= ENUMERATED {
    rlc-am,
    rlc-um-bidirectional,
    rlc-um-unidirectional-ul,
    rlc-um-unidirectional-dl,
    ...
}

RLC-Status ::= SEQUENCE {
    reestablishment-Indication  Reestablishment-Indication,
    iE-Extensions               ProtocolExtensionContainer { {RLC-Status-ExtIEs} } OPTIONAL,
    ...
}

RLC-Status-ExtIEs X2AP-PROTOCOL-EXTENSION ::= {
    ...
}

RNTP-Threshold ::= ENUMERATED {
    minusInfinity,
    minusEleven,
    minusTen,
    minusNine,
    minusEight,
    minusSeven,
    minusSix,
    minusFive,
    minusFour,
    minusThree,
    minusTwo,
    minusOne,
    zero,
    one,
    two,
    three,
    ...
}

RRC-Config-Ind ::= ENUMERATED {
    full-config,
    delta-config,
    ...
}

RRC-Context ::= OCTET STRING

RRCConnReestabIndicator ::= ENUMERATED {
    reconfigurationFailure, handoverFailure, otherFailure, ...
}
-- The values correspond to the values of ReestablishmentCause reported from the UE in the RRCConnectionReestablishmentRequest, as defined in TS 36.331 [9]

RRCConnSetupIndicator::= ENUMERATED {
    rrcConnSetup,
    ...
}

RSRPMeasurementResult ::= SEQUENCE (SIZE(1..maxCellReport)) OF
    SEQUENCE {
        rSRPCellID                      ECGI,
        rSRPMeasured                    INTEGER (0..97, ...),
        iE-Extensions                   ProtocolExtensionContainer { {RSRPMeasurementResult-ExtIEs} } OPTIONAL,
        ...
    }

RSRPMeasurementResult-ExtIEs X2AP-PROTOCOL-EXTENSION ::= {
    ...
}

RSRPMRList ::= SEQUENCE (SIZE(1..maxUEReport)) OF
    SEQUENCE {
        rSRPMeasurementResult           RSRPMeasurementResult,
        iE-Extensions                   ProtocolExtensionContainer { {RSRPMRList-ExtIEs} } OPTIONAL,
        ...
    }

RSRPMRList-ExtIEs X2AP-PROTOCOL-EXTENSION ::= {
    { ID id-UEID    CRITICALITY ignore  EXTENSION UEID      PRESENCE optional},
    ...
}

RRCContainer ::= OCTET STRING

RaReportIndicationList   ::= SEQUENCE (SIZE(1..maxnoofUEsforRAReportIndications)) OF RaReportIndicationList-Item

RaReportIndicationList-Item ::= SEQUENCE {
    meNB-UE-X2AP-ID             UE-X2AP-ID,
    meNB-UE-X2AP-ID-Extension   UE-X2AP-ID-Extension                                                OPTIONAL,
    iE-Extensions               ProtocolExtensionContainer { {RaReportIndicationList-Item-ExtIEs} } OPTIONAL,
    ...
}

RaReportIndicationList-Item-ExtIEs X2AP-PROTOCOL-EXTENSION::= {
    ...
}

-- S

S1TNLLoadIndicator ::= SEQUENCE {
    dLS1TNLLoadIndicator            LoadIndicator,
    uLS1TNLLoadIndicator            LoadIndicator,
    iE-Extensions                   ProtocolExtensionContainer { {S1TNLLoadIndicator-ExtIEs} } OPTIONAL,
    ...
}

S1TNLLoadIndicator-ExtIEs X2AP-PROTOCOL-EXTENSION ::= {
    ...
}


SCGActivationStatus ::= ENUMERATED {scg-activated, scg-deactivated, ...}


SCGActivationRequest ::= ENUMERATED {activate-scg, deactivate-scg, ...}


SCGChangeIndication ::= ENUMERATED {pDCPCountWrapAround, pSCellChange, other, ...}

SCGreconfigNotification ::= ENUMERATED {executed, ..., executed-deleted, deleted }


SCG-UE-HistoryInformation ::= SEQUENCE (SIZE(1.. maxnoofPSCellsPerSN)) OF LastVisitedPSCell-Item

SecondaryRATUsageReportList ::= SEQUENCE (SIZE(1..maxnoofBearers)) OF ProtocolIE-Single-Container {{SecondaryRATUsageReport-ItemIEs}}

SecondaryRATUsageReport-ItemIEs X2AP-PROTOCOL-IES ::= {
    { ID id-SecondaryRATUsageReport-Item        CRITICALITY reject  TYPE SecondaryRATUsageReport-Item       PRESENCE mandatory},
    ...
}

SecondaryRATUsageReport-Item ::= SEQUENCE {
    e-RAB-ID                        E-RAB-ID,
    secondaryRATType                ENUMERATED {nr, ..., nR-unlicensed },
    e-RABUsageReportList            E-RABUsageReportList,
    iE-Extensions               ProtocolExtensionContainer { {SecondaryRATUsageReport-Item-ExtIEs} } OPTIONAL,
...
}

SecondaryRATUsageReport-Item-ExtIEs X2AP-PROTOCOL-EXTENSION ::= {
    ...
}

SecurityIndication ::= SEQUENCE {
    integrityProtectionIndication           IntegrityProtectionIndication,
    iE-Extensions                           ProtocolExtensionContainer { { SecurityIndication-ExtIEs } } OPTIONAL,
    ...
}

SecurityIndication-ExtIEs X2AP-PROTOCOL-EXTENSION ::= {
    ...
}

SecurityResult ::= SEQUENCE {
    integrityProtectionResult           IntegrityProtectionResult,
    iE-Extensions                       ProtocolExtensionContainer { {SecurityResult-ExtIEs} }  OPTIONAL,
    ...
}

SecurityResult-ExtIEs X2AP-PROTOCOL-EXTENSION ::= {
    ...
}

SeNBSecurityKey ::= BIT STRING (SIZE(256))

SeNBtoMeNBContainer ::= OCTET STRING

SensorMeasurementConfiguration ::=  SEQUENCE {
    sensorMeasConfig            SensorMeasConfig,
    sensorMeasConfigNameList    SensorMeasConfigNameList                                        OPTIONAL,
    iE-Extensions       ProtocolExtensionContainer { {SensorMeasurementConfiguration-ExtIEs} }  OPTIONAL,
    ...
}

SensorMeasurementConfiguration-ExtIEs X2AP-PROTOCOL-EXTENSION ::= {
    ...
}

SensorMeasConfigNameList ::= SEQUENCE (SIZE(1..maxnoofSensorName)) OF SensorMeasConfigNameItem

SensorMeasConfigNameItem ::= SEQUENCE {
    sensorNameConfig        SensorNameConfig,
    iE-Extensions       ProtocolExtensionContainer { { SensorMeasConfigNameItem-ExtIEs } }  OPTIONAL,
    ...
}

SensorMeasConfigNameItem-ExtIEs X2AP-PROTOCOL-EXTENSION ::= {
    ...
}

SensorMeasConfig::= ENUMERATED {setup,...}

SensorNameConfig ::= CHOICE {
    uncompensatedBarometricConfig       ENUMERATED {true, ...},
    choice-extension        ProtocolIE-Single-Container { {SensorNameConfig-ExtIEs} }
}

SensorNameConfig-ExtIEs X2AP-PROTOCOL-IES ::= {
    ...
}


ServedCells ::= SEQUENCE (SIZE (1.. maxCellineNB)) OF SEQUENCE {
    servedCellInfo                  ServedCell-Information,
    neighbour-Info                  Neighbour-Information           OPTIONAL,
    iE-Extensions                   ProtocolExtensionContainer { {ServedCell-ExtIEs} } OPTIONAL,
    ...
}

ServedCell-ExtIEs X2AP-PROTOCOL-EXTENSION ::= {
    { ID id-NRNeighbourInfoToAdd            CRITICALITY ignore  EXTENSION NRNeighbour-Information               PRESENCE optional }|
    { ID id-ServedCellSpecificInfoReq-NR    CRITICALITY ignore EXTENSION    ServedCellSpecificInfoReq-NR    PRESENCE optional },
    ...
}

ServedCell-Information ::= SEQUENCE {
    pCI                 PCI,
    cellId              ECGI,
    tAC                 TAC,
    broadcastPLMNs      BroadcastPLMNs-Item,
    eUTRA-Mode-Info     EUTRA-Mode-Info,
    iE-Extensions       ProtocolExtensionContainer { {ServedCell-Information-ExtIEs} } OPTIONAL,
    ...
}

ServedCell-Information-ExtIEs X2AP-PROTOCOL-EXTENSION ::= {
    { ID id-Number-of-Antennaports              CRITICALITY ignore  EXTENSION Number-of-Antennaports                    PRESENCE optional}|
    { ID id-PRACH-Configuration                 CRITICALITY ignore  EXTENSION PRACH-Configuration                       PRESENCE optional}|
    { ID id-MBSFN-Subframe-Info                 CRITICALITY ignore  EXTENSION MBSFN-Subframe-Infolist               PRESENCE optional}|
    { ID id-CSG-Id                              CRITICALITY ignore  EXTENSION CSG-Id                                    PRESENCE optional}|
    { ID id-MBMS-Service-Area-List              CRITICALITY ignore  EXTENSION MBMS-Service-Area-Identity-List       PRESENCE optional}|
    { ID id-MultibandInfoList                   CRITICALITY ignore  EXTENSION MultibandInfoList                         PRESENCE optional}|
    { ID id-FreqBandIndicatorPriority           CRITICALITY ignore  EXTENSION FreqBandIndicatorPriority             PRESENCE optional}|
    { ID id-BandwidthReducedSI                  CRITICALITY ignore  EXTENSION BandwidthReducedSI                        PRESENCE optional}|
    { ID id-ProtectedEUTRAResourceIndication    CRITICALITY ignore  EXTENSION ProtectedEUTRAResourceIndication  PRESENCE optional}|
    { ID id-BPLMN-ID-Info-EUTRA                 CRITICALITY ignore  EXTENSION BPLMN-ID-Info-EUTRA                       PRESENCE optional}|
    { ID id-NPRACHConfiguration                 CRITICALITY ignore  EXTENSION   NPRACHConfiguration                 PRESENCE optional}|
    { ID id-SFN-Offset                          CRITICALITY ignore  EXTENSION SFN-Offset                                PRESENCE optional},
    ...
}

ServedCellSpecificInfoReq-NR    ::= SEQUENCE (SIZE(1.. maxCellinengNB)) OF ServedCellSpecificInfoReq-NR-Item

ServedCellSpecificInfoReq-NR-Item   ::= SEQUENCE {
    nRCGI                                   NRCGI,
    additionalMTCListRequestIndicator       ENUMERATED {additionalMTCListRequested, ...}            OPTIONAL,
    iE-Extensions                           ProtocolExtensionContainer { { ServedCellSpecificInfoReq-NR-Item-ExtIEs} }  OPTIONAL,
    ...
}

ServedCellSpecificInfoReq-NR-Item-ExtIEs X2AP-PROTOCOL-EXTENSION ::= {
    ...
}


ServiceType ::= ENUMERATED{
    qMC-for-streaming-service,
    qMC-for-MTSI-service,
    ...
}

SgNBCoordinationAssistanceInformation ::= ENUMERATED{
    coordination-not-required,
    ...
}

SgNBResourceCoordinationInformation ::= SEQUENCE {
    nR-CGI                          NRCGI,
    uLCoordinationInformation       BIT STRING (SIZE(6..4400, ...)),
    dLCoordinationInformation       BIT STRING (SIZE(6..4400, ...)) OPTIONAL,
    iE-Extensions                   ProtocolExtensionContainer { {SgNBResourceCoordinationInformationExtIEs} }       OPTIONAL,
    ...
}

SgNBResourceCoordinationInformationExtIEs X2AP-PROTOCOL-EXTENSION ::= {
    { ID id-ECGI                                        CRITICALITY ignore  EXTENSION ECGI                                              PRESENCE optional}|
    { ID id-SgNBCoordinationAssistanceInformation       CRITICALITY reject  EXTENSION SgNBCoordinationAssistanceInformation PRESENCE optional},
    ...
}

SgNB-UE-X2AP-ID ::= INTEGER (0..4294967295)

SIPTOBearerDeactivationIndication ::= ENUMERATED {
    true,
    ...
}

SharedResourceType ::= CHOICE{
    uLOnlySharing       ULOnlySharing,
    uLandDLSharing      ULandDLSharing,
    ...
}

ShortMAC-I ::= BIT STRING (SIZE(16))


SGNB-Addition-Trigger-Ind    ::= ENUMERATED {
    sn-change,
    inter-eNB-HO,
    intra-eNB-HO,
    ...
}

SNtriggered ::=ENUMERATED{
    true,
    ...
}

SourceOfUEActivityBehaviourInformation ::= ENUMERATED {
    subscription-information,
    statistics,
    ...
}

SpecialSubframe-Info ::= SEQUENCE {
    specialSubframePatterns     SpecialSubframePatterns,
    cyclicPrefixDL              CyclicPrefixDL,
    cyclicPrefixUL              CyclicPrefixUL,
    iE-Extensions               ProtocolExtensionContainer { {SpecialSubframe-Info-ExtIEs} } OPTIONAL,
    ...
}

SpecialSubframe-Info-ExtIEs X2AP-PROTOCOL-EXTENSION ::= {
    ...
}

SpecialSubframePatterns ::= ENUMERATED {
    ssp0,
    ssp1,
    ssp2,
    ssp3,
    ssp4,
    ssp5,
    ssp6,
    ssp7,
    ssp8,
    ...
}

SpectrumSharingGroupID ::= INTEGER (1..maxCellineNB)

SubbandCQI ::= SEQUENCE {
    subbandCQICodeword0         SubbandCQICodeword0,
    subbandCQICodeword1         SubbandCQICodeword1     OPTIONAL,
    iE-Extensions               ProtocolExtensionContainer { {SubbandCQI-ExtIEs} } OPTIONAL,
    ...
}

Subscription-Based-UE-DifferentiationInfo ::= SEQUENCE {
    periodicCommunicationIndicator  ENUMERATED {periodically, ondemand, ...}        OPTIONAL,
    periodicTime                    INTEGER (1..3600, ...)                          OPTIONAL,
    scheduledCommunicationTime      ScheduledCommunicationTime                      OPTIONAL,
    stationaryIndication            ENUMERATED {stationary, mobile, ...}            OPTIONAL,
    trafficProfile                  ENUMERATED {single-packet, dual-packets, multiple-packets, ...}             OPTIONAL,
    batteryIndication               ENUMERATED {battery-powered, battery-powered-not-rechargeable-or-replaceable, not-battery-powered, ...}     OPTIONAL,
    iE-Extensions                   ProtocolExtensionContainer { { Subscription-Based-UE-DifferentiationInfo-ExtIEs} } OPTIONAL,
    ...
}

Subscription-Based-UE-DifferentiationInfo-ExtIEs X2AP-PROTOCOL-EXTENSION ::= {
    ...
}

ScheduledCommunicationTime ::= SEQUENCE {
    dayofWeek               BIT STRING (SIZE(7))                                    OPTIONAL,
    timeofDayStart          INTEGER (0..86399, ...)                                 OPTIONAL,
    timeofDayEnd            INTEGER (0..86399, ...)                                 OPTIONAL,
    iE-Extensions           ProtocolExtensionContainer { { ScheduledCommunicationTime-ExtIEs}}  OPTIONAL,
    ...
}

ScheduledCommunicationTime-ExtIEs X2AP-PROTOCOL-EXTENSION ::= {
    ...
}

SRVCCOperationPossible ::= ENUMERATED {
    possible,
    ...
}

SSBAreaCapacityValue-List   ::= SEQUENCE (SIZE (1.. maxnoofSSBAreas)) OF SSBAreaCapacityValue-Item

SSBAreaCapacityValue-Item   ::=     SEQUENCE {
    ssbIndex                            SSBIndex,
    ssbAreaCapacityValue                INTEGER (0..100),
    iE-Extensions                       ProtocolExtensionContainer { {SSBAreaCapacityValue-ExtIEs} } OPTIONAL,
    ...
}

SSBAreaCapacityValue-ExtIEs X2AP-PROTOCOL-EXTENSION ::= {
    ...
}

SSBAreaRadioResourceStatus-List ::= SEQUENCE (SIZE (1.. maxnoofSSBAreas)) OF SSBAreaRadioResourceStatus-Item

SSBAreaRadioResourceStatus-Item ::= SEQUENCE {
    ssbIndex                            SSBIndex,
    ssbAreaDLGBRPRBUsage                INTEGER (0..100),
    ssbAreaULGBRPRBUsage                INTEGER (0..100),
    ssbAreaDLNonGBRPRBUsage             INTEGER (0..100),
    ssbAreaULNonGBRPRBUsage             INTEGER (0..100),
    ssbAreaDLTotalPRBUsage              INTEGER (0..100),
    ssbAreaULTotalPRBUsage              INTEGER (0..100),
    ssbAreaDLSchedulingPDCCHCCEUsage    INTEGER (0..100)                                    OPTIONAL,
    ssbAreaULSchedulingPDCCHCCEUsage    INTEGER (0..100)                                    OPTIONAL,
    iE-Extensions                       ProtocolExtensionContainer { {SSBAreaRadioResourceStatus-ExtIEs} } OPTIONAL,
    ...
}

SSBAreaRadioResourceStatus-ExtIEs X2AP-PROTOCOL-EXTENSION ::= {
    ...
}

SSBIndex ::= INTEGER (0..63)

SSB-PositionsInBurst ::= CHOICE {
    shortBitmap                     BIT STRING (SIZE (4)),
    mediumBitmap                    BIT STRING (SIZE (8)),
    longBitmap                      BIT STRING (SIZE (64)),
    choice-extension                ProtocolIE-Single-Container { {SSB-PositionsInBurst-ExtIEs} }
}

SSB-PositionsInBurst-ExtIEs X2AP-PROTOCOL-IES ::= {
    ...
}


SubbandCQI-ExtIEs X2AP-PROTOCOL-EXTENSION ::= {
    ...
}

SubbandCQICodeword0 ::= CHOICE {
    four-bitCQI                     INTEGER (0..15, ...),
    two-bitSubbandDifferentialCQI   INTEGER (0..3, ...),
    two-bitDifferentialCQI          INTEGER (0..3, ...),
    ...
}
SubbandCQICodeword1 ::= CHOICE {
    four-bitCQI                         INTEGER (0..15, ...),
    three-bitSpatialDifferentialCQI     INTEGER (0..7, ...),
    two-bitSubbandDifferentialCQI       INTEGER (0..3, ...),
    two-bitDifferentialCQI              INTEGER (0..3, ...),
    ...
}

SubbandCQIList ::= SEQUENCE (SIZE(1.. maxSubband)) OF SubbandCQIItem

SubbandCQIItem ::= SEQUENCE {
    subbandCQI          SubbandCQI,
    subbandIndex        INTEGER (0..27,...),
    iE-Extensions       ProtocolExtensionContainer { {SubbandCQIItem-ExtIEs} } OPTIONAL,
    ...
}

SubbandCQIItem-ExtIEs X2AP-PROTOCOL-EXTENSION ::= {
    ...
}

SubbandSize ::= ENUMERATED {
    size2,
    size3,
    size4,
    size6,
    size8,
    ...
}

SubscriberProfileIDforRFP ::= INTEGER (1..256)

SubframeAllocation ::= CHOICE {
    oneframe                        Oneframe,
    fourframes                      Fourframes,
    ...
}

SubframeAssignment ::= ENUMERATED {
    sa0,
    sa1,
    sa2,
    sa3,
    sa4,
    sa5,
    sa6,
    ...
}

SubframeType ::= ENUMERATED{mbsfn,nonmbsfn,...}

SgNBSecurityKey ::= BIT STRING (SIZE(256))

SgNBtoMeNBContainer ::= OCTET STRING

SRBType ::= ENUMERATED {srb1, srb2, ...}
SCGConfigurationQuery ::= ENUMERATED {true,...}

SULInformation ::= SEQUENCE {
    sUL-ARFCN               INTEGER (0.. 3279165),
    sUL-TxBW                NR-TxBW,
    iE-Extensions           ProtocolExtensionContainer { {SULInformation-ExtIEs} }      OPTIONAL,
    ...
}


SupportedSULFreqBandItem ::= SEQUENCE {
    freqBandIndicatorNr             INTEGER (1..1024,...),
    iE-Extensions           ProtocolExtensionContainer { {SupportedSULFreqBandItem-ExtIEs} }        OPTIONAL,
    ...
}

SupportedSULFreqBandItem-ExtIEs X2AP-PROTOCOL-EXTENSION ::= {
    ...
}

SULInformation-ExtIEs X2AP-PROTOCOL-EXTENSION ::= {
    { ID id-CarrierList                     CRITICALITY ignore  EXTENSION NRCarrierList         PRESENCE optional }|
    { ID id-FrequencyShift7p5khz            CRITICALITY ignore  EXTENSION FrequencyShift7p5khz  PRESENCE optional },
    ...
}

SFN-Offset ::= SEQUENCE {
    sFN-Time-Offset                 BIT STRING (SIZE(24)),
    iE-Extensions       ProtocolExtensionContainer { {SFN-Offset-ExtIEs} } OPTIONAL,
    ...
}

SFN-Offset-ExtIEs X2AP-PROTOCOL-EXTENSION ::= {
        ...
}

-- T

TABasedMDT::= SEQUENCE {
    tAListforMDT        TAListforMDT,
    iE-Extensions       ProtocolExtensionContainer { {TABasedMDT-ExtIEs} } OPTIONAL,
    ...
}

TABasedMDT-ExtIEs X2AP-PROTOCOL-EXTENSION ::= {
    ...
}

TAC ::= OCTET STRING (SIZE (2))

TAIBasedMDT ::= SEQUENCE {
    tAIListforMDT           TAIListforMDT,
    iE-Extensions           ProtocolExtensionContainer { {TAIBasedMDT-ExtIEs} } OPTIONAL,
    ...
}

TAIBasedMDT-ExtIEs X2AP-PROTOCOL-EXTENSION ::= {
    ...
}

TAIListforMDT ::= SEQUENCE (SIZE(1..maxnoofTAforMDT)) OF TAI-Item

TAI-Item ::= SEQUENCE {
    tAC                 TAC,
    pLMN-Identity       PLMN-Identity,
    iE-Extensions       ProtocolExtensionContainer { {TAI-Item-ExtIEs} } OPTIONAL,
    ...
}

TAI-Item-ExtIEs X2AP-PROTOCOL-EXTENSION ::= {
    ...
}

TAListforMDT ::= SEQUENCE (SIZE(1..maxnoofTAforMDT)) OF TAC

TABasedQMC ::= SEQUENCE {
    tAListforQMC        TAListforQMC,
    iE-Extensions       ProtocolExtensionContainer { {TABasedQMC-ExtIEs} } OPTIONAL,
    ...
}

TABasedQMC-ExtIEs X2AP-PROTOCOL-EXTENSION ::= {
    ...
}

TAListforQMC ::= SEQUENCE (SIZE(1..maxnoofTAforQMC)) OF TAC

TAIBasedQMC ::= SEQUENCE {
    tAIListforQMC       TAIListforQMC,
    iE-Extensions       ProtocolExtensionContainer { {TAIBasedQMC-ExtIEs} } OPTIONAL,
    ...
}

TAIBasedQMC-ExtIEs X2AP-PROTOCOL-EXTENSION ::= {
    ...
}

TAIListforQMC ::= SEQUENCE (SIZE(1..maxnoofTAforQMC)) OF TAI-Item

TargetCellInNGRAN ::= OCTET STRING

TargetCellInUTRAN ::= OCTET STRING -- This IE is to be encoded according to the UTRAN Cell ID in the Last Visited UTRAN Cell Information IE in TS 25.413 [24]

TargeteNBtoSource-eNBTransparentContainer   ::= OCTET STRING

TDD-Info ::= SEQUENCE {
    eARFCN                          EARFCN,
    transmission-Bandwidth          Transmission-Bandwidth,
    subframeAssignment              SubframeAssignment,
    specialSubframe-Info            SpecialSubframe-Info,
    iE-Extensions                   ProtocolExtensionContainer { {TDD-Info-ExtIEs} } OPTIONAL,
    ...
}

TDD-Info-ExtIEs X2AP-PROTOCOL-EXTENSION ::= {
    { ID id-AdditionalSpecialSubframe-Info          CRITICALITY ignore  EXTENSION AdditionalSpecialSubframe-Info                PRESENCE optional}|
    { ID id-eARFCNExtension                         CRITICALITY reject  EXTENSION EARFCNExtension                                   PRESENCE optional}|
    { ID id-AdditionalSpecialSubframeExtension-Info CRITICALITY ignore  EXTENSION AdditionalSpecialSubframeExtension-Info   PRESENCE optional}|
    { ID id-OffsetOfNbiotChannelNumberToDL-EARFCN   CRITICALITY reject  EXTENSION OffsetOfNbiotChannelNumberToEARFCN        PRESENCE optional}|
    { ID id-NBIoT-UL-DL-AlignmentOffset             CRITICALITY reject  EXTENSION NBIoT-UL-DL-AlignmentOffset                   PRESENCE optional},
    ...
}

TDD-InfoNeighbourServedNRCell-Information ::= SEQUENCE {
    nRFreqInfo              NRFreqInfo,
    iE-Extensions           ProtocolExtensionContainer { {TDD-InfoNeighbourServedNRCell-Information-ExtIEs} }       OPTIONAL,
    ...
}

TDD-InfoNeighbourServedNRCell-Information-ExtIEs X2AP-PROTOCOL-EXTENSION ::= {
    {ID id-IntendedTDD-DL-ULConfiguration-NR    CRITICALITY ignore  EXTENSION IntendedTDD-DL-ULConfiguration-NR     PRESENCE optional}|
    {ID id-TDDULDLConfigurationCommonNR         CRITICALITY ignore  EXTENSION TDDULDLConfigurationCommonNR              PRESENCE optional}|
    {ID id-CarrierList                          CRITICALITY ignore  EXTENSION NRCarrierList                                 PRESENCE optional},
    ...
}

TDDULDLConfigurationCommonNR ::= OCTET STRING


Threshold-RSRP ::= INTEGER(0..97)

Threshold-RSRQ ::= INTEGER(0..34)

TimeToWait ::= ENUMERATED {
    v1s,
    v2s,
    v5s,
    v10s,
    v20s,
    v60s,
    ...
}

Time-UE-StayedInCell ::= INTEGER (0..4095)

Time-UE-StayedInCell-EnhancedGranularity ::= INTEGER (0..40950)

TNLA-To-Add-List ::= SEQUENCE (SIZE(1..maxnoofTNLAssociations)) OF TNLA-To-Add-Item

TNLA-To-Add-Item ::= SEQUENCE {
    tNLAssociationTransportLayerAddress     CPTransportLayerInformation,
    tNLAssociationUsage                     TNLAssociationUsage,
    iE-Extensions                           ProtocolExtensionContainer { { TNLA-To-Add-Item-ExtIEs} } OPTIONAL
}

TNLA-To-Add-Item-ExtIEs X2AP-PROTOCOL-EXTENSION ::= {
    ...
}

TNLA-To-Update-List ::= SEQUENCE (SIZE(1..maxnoofTNLAssociations)) OF TNLA-To-Update-Item

TNLA-To-Update-Item::= SEQUENCE {
    tNLAssociationTransportLayerAddress     CPTransportLayerInformation,
    tNLAssociationUsage                     TNLAssociationUsage         OPTIONAL,
    iE-Extensions                           ProtocolExtensionContainer { { TNLA-To-Update-Item-ExtIEs} } OPTIONAL
}

TNLA-To-Update-Item-ExtIEs X2AP-PROTOCOL-EXTENSION ::= {
    ...
}

TNLA-To-Remove-List ::= SEQUENCE (SIZE(1..maxnoofTNLAssociations)) OF TNLA-To-Remove-Item

TNLA-To-Remove-Item::= SEQUENCE {
    tNLAssociationTransportLayerAddress     CPTransportLayerInformation,
    iE-Extensions                           ProtocolExtensionContainer { { TNLA-To-Remove-Item-ExtIEs} } OPTIONAL
}

TNLA-To-Remove-Item-ExtIEs X2AP-PROTOCOL-EXTENSION ::= {
    ...
}

TNLA-Setup-List ::= SEQUENCE (SIZE(1..maxnoofTNLAssociations)) OF TNLA-Setup-Item

TNLA-Setup-Item ::= SEQUENCE {
    tNLAssociationTransportLayerAddress     CPTransportLayerInformation,
    iE-Extensions                           ProtocolExtensionContainer { { TNLA-Setup-Item-ExtIEs} } OPTIONAL,
    ...
}

TNLA-Setup-Item-ExtIEs X2AP-PROTOCOL-EXTENSION ::= {
    ...
}

TNLA-Failed-To-Setup-List ::= SEQUENCE (SIZE(1..maxnoofTNLAssociations)) OF TNLA-Failed-To-Setup-Item

TNLA-Failed-To-Setup-Item ::= SEQUENCE {
    tNLAssociationTransportLayerAddress     CPTransportLayerInformation,
    cause                                   Cause,
    iE-Extensions                           ProtocolExtensionContainer { { TNLA-Failed-To-Setup-Item-ExtIEs} } OPTIONAL
}

TNLA-Failed-To-Setup-Item-ExtIEs X2AP-PROTOCOL-EXTENSION ::= {
    ...
}

TNLAssociationUsage ::= ENUMERATED {
    ue,
    non-ue,
    both,
    ...
}

TNLCapacityIndicator ::= SEQUENCE {
    dlTNLMaximumOfferedCapacity         INTEGER (1..16777216, ...),
    dlTNLAvailableCapacity              INTEGER (0..100, ...),
    ulTNLMaximumOfferedCapacity         INTEGER (1..16777216, ...),
    ulTNLAvailableCapacity              INTEGER (0..100, ...),
    iE-Extensions                       ProtocolExtensionContainer { {TNLCapacityIndicator-ExtIEs} } OPTIONAL,
    ...
}

TNLCapacityIndicator-ExtIEs X2AP-PROTOCOL-EXTENSION ::= {
    ...
}


Transport-UP-Layer-Addresses-Info-To-Add-List   ::= SEQUENCE (SIZE(1.. maxnoofTLAs)) OF Transport-UP-Layer-Addresses-Info-To-Add-Item

Transport-UP-Layer-Addresses-Info-To-Add-Item ::= SEQUENCE {
    iP-SecTransportLayerAddress     TransportLayerAddress,
    gTPTransportLayerAddressesToAdd         GTPTLAs                         OPTIONAL,
    iE-Extensions                   ProtocolExtensionContainer { { Transport-UP-Layer-Addresses-Info-To-Add-ItemExtIEs } }    OPTIONAL,
    ...
}

Transport-UP-Layer-Addresses-Info-To-Add-ItemExtIEs X2AP-PROTOCOL-EXTENSION ::= {
    ...
}

Transport-UP-Layer-Addresses-Info-To-Remove-List    ::= SEQUENCE (SIZE(1.. maxnoofTLAs)) OF Transport-UP-Layer-Addresses-Info-To-Remove-Item

Transport-UP-Layer-Addresses-Info-To-Remove-Item ::= SEQUENCE {
    iP-SecTransportLayerAddress     TransportLayerAddress,
    gTPTransportLayerAddressesToRemove          GTPTLAs                         OPTIONAL,
    iE-Extensions                   ProtocolExtensionContainer { { Transport-UP-Layer-Addresses-Info-To-Remove-ItemExtIEs } }    OPTIONAL,
    ...
}

Transport-UP-Layer-Addresses-Info-To-Remove-ItemExtIEs X2AP-PROTOCOL-EXTENSION ::= {
    ...
}


TNLConfigurationInfo  ::= SEQUENCE {
    transport-UP-Layer-Addresses-Info-To-Add-List       Transport-UP-Layer-Addresses-Info-To-Add-List                       OPTIONAL,
    transport-UP-Layer-Addresses-Info-To-Remove-List    Transport-UP-Layer-Addresses-Info-To-Remove-List                    OPTIONAL,
    iE-Extensions   ProtocolExtensionContainer { { TNLConfigurationInfo-ExtIEs } }                                          OPTIONAL,
    ...
}

TNLConfigurationInfo-ExtIEs     X2AP-PROTOCOL-EXTENSION ::= {
    ...
}

TraceActivation ::= SEQUENCE {
    eUTRANTraceID                   EUTRANTraceID,
    interfacesToTrace               InterfacesToTrace,
traceDepth                          TraceDepth,
traceCollectionEntityIPAddress      TraceCollectionEntityIPAddress,
    iE-Extensions                   ProtocolExtensionContainer { {TraceActivation-ExtIEs} } OPTIONAL,
    ...
}

TraceActivation-ExtIEs X2AP-PROTOCOL-EXTENSION ::= {
    { ID id-MDTConfiguration            CRITICALITY ignore  EXTENSION MDT-Configuration         PRESENCE optional}|
    { ID id-UEAppLayerMeasConfig        CRITICALITY ignore  EXTENSION UEAppLayerMeasConfig      PRESENCE optional}|
    { ID id-MDTConfigurationNR          CRITICALITY ignore  EXTENSION MDT-ConfigurationNR       PRESENCE optional}|
    { ID id-TraceCollectionEntityURI    CRITICALITY ignore  EXTENSION URI-Address               PRESENCE optional},
    ...
}

TraceCollectionEntityIPAddress ::= BIT STRING (SIZE(1..160, ...))

TraceDepth      ::= ENUMERATED {
    minimum,
    medium,
    maximum,
    minimumWithoutVendorSpecificExtension,
    mediumWithoutVendorSpecificExtension,
    maximumWithoutVendorSpecificExtension,
    ...
}

Transmission-Bandwidth ::= ENUMERATED {
        bw6,
        bw15,
        bw25,
        bw50,
        bw75,
        bw100,
        ...,
        bw1
}

TransportLayerAddress           ::= BIT STRING (SIZE(1..160, ...))

TransportLayerAddressAndPort        ::= SEQUENCE {
    endpointIPAddress               TransportLayerAddress,
    portnumber                      Port-Number
}

TunnelInformation ::= SEQUENCE {
    transportLayerAddress   TransportLayerAddress,
    uDP-Port-Number         Port-Number         OPTIONAL,
    iE-Extensions           ProtocolExtensionContainer { {Tunnel-Information-ExtIEs} } OPTIONAL,
    ...
}

Tunnel-Information-ExtIEs X2AP-PROTOCOL-EXTENSION ::= {
    ...
}

TypeOfError ::= ENUMERATED {
    not-understood,
    missing,
    ...
}


-- U

UEAggregateMaximumBitRate ::= SEQUENCE {
    uEaggregateMaximumBitRateDownlink   BitRate,
    uEaggregateMaximumBitRateUplink     BitRate,
    iE-Extensions                       ProtocolExtensionContainer { {UEAggregate-MaximumBitrate-ExtIEs} } OPTIONAL,
    ...
}

UEAggregate-MaximumBitrate-ExtIEs X2AP-PROTOCOL-EXTENSION ::= {
    { ID id-extended-uEaggregateMaximumBitRateDownlink  CRITICALITY ignore  EXTENSION ExtendedBitRate   PRESENCE optional}|
    { ID id-extended-uEaggregateMaximumBitRateUplink    CRITICALITY ignore  EXTENSION ExtendedBitRate   PRESENCE optional},
    ...
}

UEAppLayerMeasConfig ::= SEQUENCE {
    containerForAppLayerMeasConfig          OCTET STRING (SIZE(1..1000)),
    areaScopeOfQMC      AreaScopeOfQMC,
    iE-Extensions       ProtocolExtensionContainer { {UEAppLayerMeasConfig-ExtIEs} } OPTIONAL,
    ...
}

UEAppLayerMeasConfig-ExtIEs X2AP-PROTOCOL-EXTENSION ::= {
    {ID id-serviceType  CRITICALITY ignore  EXTENSION ServiceType   PRESENCE optional},
    ...
}

UE-ContextKeptIndicator ::= ENUMERATED {
    true,
    ...
}

UEID ::= BIT STRING (SIZE (16))

UE-HistoryInformation ::= SEQUENCE (SIZE(1..maxnoofCells)) OF LastVisitedCell-Item

UE-HistoryInformationFromTheUE ::= OCTET STRING
-- This IE is a transparent container and shall be encoded as the VisitedCellInfoList field contained in the UEInformationResponse message as defined in TS 36.331 [9]

UE-S1AP-ID ::= INTEGER (0.. 4294967295)

UE-X2AP-ID ::= INTEGER (0..4095)

UE-X2AP-ID-Extension ::= INTEGER (0..4095, ...)

UERadioCapability ::= OCTET STRING

UERadioCapabilityID ::= OCTET STRING

UE-RLF-Report-Container::= OCTET STRING
-- This IE is a transparent container and shall be encoded as the rLF-Report-r9 field contained in the UEInformationResponse message as defined in TS 36.331 [9]

UE-RLF-Report-Container-for-extended-bands ::= OCTET STRING
-- This IE is a transparent container and shall be encoded as the rLF-Report-v9e0 field contained in the UEInformationResponse message as defined in TS 36.331 [9]

UESecurityCapabilities ::= SEQUENCE {
    encryptionAlgorithms                EncryptionAlgorithms,
    integrityProtectionAlgorithms       IntegrityProtectionAlgorithms,
    iE-Extensions                       ProtocolExtensionContainer { {UESecurityCapabilities-ExtIEs} }      OPTIONAL,
...
}

UESecurityCapabilities-ExtIEs X2AP-PROTOCOL-EXTENSION ::= {
    ...
}

UESidelinkAggregateMaximumBitRate ::= SEQUENCE {
    uESidelinkAggregateMaximumBitRate       BitRate,
    iE-Extensions                   ProtocolExtensionContainer { {UE-Sidelink-Aggregate-MaximumBitRate-ExtIEs} } OPTIONAL,
    ...
}

UE-Sidelink-Aggregate-MaximumBitRate-ExtIEs X2AP-PROTOCOL-EXTENSION ::= {
    ...
}

UEsToBeResetList ::= SEQUENCE (SIZE (1.. maxUEsinengNBDU)) OF UEsToBeResetList-Item

UEsToBeResetList-Item::= SEQUENCE {
    meNB-ID                 UE-X2AP-ID,
    meNB-ID-ext             UE-X2AP-ID-Extension                                                        OPTIONAL,
    sgNB-ID                 SgNB-UE-X2AP-ID                                                             OPTIONAL,
    iE-Extensions           ProtocolExtensionContainer { {UEsToBeResetList-Item-ExtIEs} }               OPTIONAL,
    ...
}

UEsToBeResetList-Item-ExtIEs X2AP-PROTOCOL-EXTENSION ::= {
    ...
}

ULandDLSharing ::= SEQUENCE{
    uLResourcesULandDLSharing               ULResourcesULandDLSharing,
    dLResourcesULandDLSharing               DLResourcesULandDLSharing,
    iE-Extensions           ProtocolExtensionContainer { {ULandDLSharing-ExtIEs} }              OPTIONAL,
    ...
}

ULandDLSharing-ExtIEs X2AP-PROTOCOL-EXTENSION ::= {
    ...
}

ULConfiguration::= SEQUENCE {
    uL-PDCP         UL-UE-Configuration,
    iE-Extensions                   ProtocolExtensionContainer { {ULConfiguration-ExtIEs} } OPTIONAL,
    ...
}

ULConfiguration-ExtIEs X2AP-PROTOCOL-EXTENSION ::= {
    ...
}

UL-UE-Configuration::= ENUMERATED { no-data, shared, only, ... }

UL-GBR-PRB-usage::= INTEGER (0..100)

UL-GBR-PRB-usage-for-MIMO::= INTEGER (0..100)

UL-HighInterferenceIndicationInfo ::= SEQUENCE (SIZE(1..maxCellineNB)) OF UL-HighInterferenceIndicationInfo-Item

UL-HighInterferenceIndicationInfo-Item ::= SEQUENCE {
    target-Cell-ID                  ECGI,
    ul-interferenceindication       UL-HighInterferenceIndication,
    iE-Extensions                   ProtocolExtensionContainer { {UL-HighInterferenceIndicationInfo-Item-ExtIEs} } OPTIONAL,
    ...
}

UL-HighInterferenceIndicationInfo-Item-ExtIEs X2AP-PROTOCOL-EXTENSION ::= {
    ...
}

UL-HighInterferenceIndication ::= BIT STRING (SIZE(1..110, ...))

UL-InterferenceOverloadIndication ::= SEQUENCE (SIZE(1..maxnoofPRBs)) OF UL-InterferenceOverloadIndication-Item

UL-InterferenceOverloadIndication-Item ::= ENUMERATED {
    high-interference,
    medium-interference,
    low-interference,
    ...
}

UL-non-GBR-PRB-usage::= INTEGER (0..100)

UL-non-GBR-PRB-usage-for-MIMO::= INTEGER (0..100)

ULOnlySharing ::= SEQUENCE{
    uLResourceBitmapULOnlySharing   DataTrafficResources,
    iE-Extensions                   ProtocolExtensionContainer { {ULOnlySharing-ExtIEs} }               OPTIONAL,
    ...
}

ULOnlySharing-ExtIEs X2AP-PROTOCOL-EXTENSION ::= {
    ...
}

ULResourceBitmapULandDLSharing ::= DataTrafficResources


ULResourcesULandDLSharing ::= CHOICE {
    unchanged           NULL,
    changed             ULResourceBitmapULandDLSharing,
    ...
}

UL-scheduling-PDCCH-CCE-usage::= INTEGER (0..100)

UL-Total-PRB-usage::= INTEGER (0..100)

UL-Total-PRB-usage-for-MIMO::= INTEGER (0..100)

UnlicensedSpectrumRestriction ::= ENUMERATED {
    unlicensed-restricted,
    ...
}

URI-Address ::= VisibleString

UsableABSInformation ::= CHOICE {
    fdd                 UsableABSInformationFDD,
    tdd                 UsableABSInformationTDD,
    ...
}


UsableABSInformationFDD ::= SEQUENCE {
    usable-abs-pattern-info             BIT STRING (SIZE(40)),
    iE-Extensions                       ProtocolExtensionContainer { {UsableABSInformationFDD-ExtIEs} } OPTIONAL,
    ...
}

UsableABSInformationFDD-ExtIEs X2AP-PROTOCOL-EXTENSION ::= {
    ...
}

UsableABSInformationTDD ::= SEQUENCE {
    usaable-abs-pattern-info            BIT STRING (SIZE(1..70, ...)),
    iE-Extensions                       ProtocolExtensionContainer { {UsableABSInformationTDD-ExtIEs} } OPTIONAL,
    ...
}

UsableABSInformationTDD-ExtIEs X2AP-PROTOCOL-EXTENSION ::= {
    ...
}


UserPlaneTrafficActivityReport ::= ENUMERATED {inactive, re-activated, ...}

-- V

V2XServicesAuthorized ::= SEQUENCE {
    vehicleUE           VehicleUE                                                       OPTIONAL,
pedestrianUE            PedestrianUE                                                    OPTIONAL,
    iE-Extensions       ProtocolExtensionContainer { {V2XServicesAuthorized-ExtIEs} }   OPTIONAL,
    ...
}

V2XServicesAuthorized-ExtIEs X2AP-PROTOCOL-EXTENSION ::= {
    ...
}

VehicleUE ::= ENUMERATED {
    authorized,
    not-authorized,
    ...
}

PedestrianUE ::= ENUMERATED {
    authorized,
    not-authorized,
    ...
}

-- W

WidebandCQI ::= SEQUENCE {
    widebandCQICodeword0        INTEGER (0..15, ...),
    widebandCQICodeword1        WidebandCQICodeword1        OPTIONAL,
    iE-Extensions               ProtocolExtensionContainer { {WidebandCQI-ExtIEs} } OPTIONAL,
    ...
}

WidebandCQI-ExtIEs X2AP-PROTOCOL-EXTENSION ::= {
    ...
}

WidebandCQICodeword1::= CHOICE {
    four-bitCQI                             INTEGER (0..15, ...),
    three-bitSpatialDifferentialCQI         INTEGER (0..7, ...),
    ...
}

WLANMeasurementConfiguration ::= SEQUENCE {
    wlanMeasConfig              WLANMeasConfig,
    wlanMeasConfigNameList      WLANMeasConfigNameList              OPTIONAL,
    wlan-rssi                   ENUMERATED {true, ...}              OPTIONAL,
    wlan-rtt                    ENUMERATED {true, ...}              OPTIONAL,
    iE-Extensions       ProtocolExtensionContainer { {WLANMeasurementConfiguration-ExtIEs} } OPTIONAL,
    ...
}

WLANMeasurementConfiguration-ExtIEs X2AP-PROTOCOL-EXTENSION ::= {
    ...
}

WLANMeasConfigNameList ::= SEQUENCE (SIZE(1..maxnoofWLANName)) OF WLANName

WLANMeasConfig::= ENUMERATED {setup,...}

WLANName ::= OCTET STRING (SIZE (1..32))

WTID ::= CHOICE {
    wTID-Type1          WTID-Type1,
    wTID-Type2          WTID-Long-Type2,
    ...
}

WTID-Type1 ::= SEQUENCE {
    pLMN-Identity                   PLMN-Identity,
    shortWTID                       BIT STRING (SIZE(24)),
    ...
}

WTID-Long-Type2 ::= BIT STRING (SIZE(48))

WT-UE-XwAP-ID ::= OCTET STRING (SIZE (3))

-- X

X2BenefitValue ::= INTEGER (1..8, ...)

-- Y
-- Z

END
