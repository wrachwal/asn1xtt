-- ASN1START
-- **************************************************************
--
-- PDU definitions for X2AP.
--
-- **************************************************************

X2AP-PDU-Contents {
itu-t (0) identified-organization (4) etsi (0) mobileDomain (0)
eps-Access (21) modules (3) x2ap (2) version1 (1) x2ap-PDU-Contents (1) }

DEFINITIONS AUTOMATIC TAGS ::=

BEGIN

-- **************************************************************
--
-- IE parameter types from other modules.
--
-- **************************************************************

IMPORTS
    ABSInformation,
    ABS-Status,
    AS-SecurityInformation,
    BearerType,
    Cause,
    CompositeAvailableCapacityGroup,
    Correlation-ID,
    COUNTvalue,
    CellReportingIndicator,
    AerialUEsubscriptionInformation,
    CriticalityDiagnostics,
    CRNTI,
    CSGMembershipStatus,
    CSG-Id,
    DeactivationIndication,
    DL-Forwarding,
    DynamicDLTransmissionInformation,
    E-RABsSubjectToDLDiscarding-List,
    E-RABsSubjectToEarlyStatusTransfer-List,
    ECGI,
    E-RAB-ID,
    E-RAB-Level-QoS-Parameters,
    E-RAB-List,
    EUTRANTraceID,
    GlobalENB-ID,
    GTPtunnelEndpoint,
    GUGroupIDList,
    GUMMEI,
    HandoverReportType,
    HandoverRestrictionList,
    Masked-IMEISV,
    InvokeIndication,
    LocationReportingInformation,
    LowerLayerPresenceStatusChange,
    MDT-Configuration,
    ManagementBasedMDTallowed,
    MDTPLMNList,
    Neighbour-Information,
    PCI,
    PDCP-SN,
    PLMN-Identity,
    ReceiveStatusofULPDCPSDUs,
    Registration-Request,
    RelativeNarrowbandTxPower,
    RadioResourceStatus,
    RLC-Status,
    RRCConnReestabIndicator,
    RRCConnSetupIndicator,
    UE-RLF-Report-Container,
    UEAppLayerMeasConfig,
    RRC-Context,
    ServedCell-Information,
    ServedCells,
    ShortMAC-I,
    SRVCCOperationPossible,
    SubscriberProfileIDforRFP,
    TargetCellInUTRAN,
    TargeteNBtoSource-eNBTransparentContainer,
    TimeToWait,
    TraceActivation,
    TraceDepth,
    TransportLayerAddress,
    UEAggregateMaximumBitRate,
    UE-HistoryInformation,
    UE-HistoryInformationFromTheUE,
    UE-S1AP-ID,
    UESecurityCapabilities,
    UEsToBeResetList,
    UE-X2AP-ID,
    UL-HighInterferenceIndicationInfo,
    UL-InterferenceOverloadIndication,
    HWLoadIndicator,
    S1TNLLoadIndicator,
    Measurement-ID,
    ReportCharacteristics,
    MobilityParametersInformation,
    MobilityParametersModificationRange,
    ReceiveStatusOfULPDCPSDUsExtended,
    COUNTValueExtended,
    SubframeAssignment,
    ExtendedULInterferenceOverloadInfo,
    ExpectedUEBehaviour,
    SeNBSecurityKey,
    MeNBtoSeNBContainer,
    SeNBtoMeNBContainer,
    SCGChangeIndication,
    CoMPInformation,
    ReportingPeriodicityRSRPMR,
    RSRPMRList,
    UE-RLF-Report-Container-for-extended-bands,
    ProSeAuthorized,
    CoverageModificationList,
    ReportingPeriodicityCSIR,
    CSIReportList,
    ReceiveStatusOfULPDCPSDUsPDCP-SNlength18,
    COUNTvaluePDCP-SNlength18,
    LHN-ID,
    UE-ContextKeptIndicator,
    UE-X2AP-ID-Extension,
    SIPTOBearerDeactivationIndication,
    TunnelInformation,
    V2XServicesAuthorized,
    X2BenefitValue,
    ResumeID,
    EUTRANCellIdentifier,
    MakeBeforeBreakIndicator,
    WTID,
    WT-UE-XwAP-ID,
    UESidelinkAggregateMaximumBitRate,
    SgNBSecurityKey,
    MeNBtoSgNBContainer,
    SgNBtoMeNBContainer,
    SplitSRBs,
    RRCContainer,
    SRBType,
    GlobalGNB-ID,
    GNB-ID,
    SCGConfigurationQuery,
    SplitSRB,
    NRUeReport,
    EN-DC-ResourceConfiguration,
    TAC,
    NRFreqInfo,
    NRCGI,
    NRPCI,
    NRUESecurityCapabilities,
    PDCPChangeIndication,
    ULConfiguration,
    SgNB-UE-X2AP-ID,
    SecondaryRATUsageReportList,
    ActivationID,
    MeNBResourceCoordinationInformation,
    SgNBResourceCoordinationInformation,
    NR-TxBW,
    BroadcastPLMNs-Item,
    AdditionalPLMNs-Item,
    RLCMode,
    GBR-QosInformation,
    DRB-ID,
    FiveGS-TAC,
    SULInformation,
    Packet-LossRate,
    ResourceType,
    DataTrafficResourceIndication,
    SpectrumSharingGroupID,
    RRC-Config-Ind,
    SGNB-Addition-Trigger-Ind,
    UserPlaneTrafficActivityReport,
    ERABActivityNotifyItemList,
    PDCPSnLength,
    Subscription-Based-UE-DifferentiationInfo,
    LCID,
    DuplicationActivation,
    GNBOverloadInformation,
    NewDRBIDrequest,
    DesiredActNotificationLevel,
    LocationInformationSgNB,
    LocationInformationSgNBReporting,
    EndcSONConfigurationTransfer,
    NRNeighbour-Information,
    InterfaceInstanceIndication,
    BPLMN-ID-Info-NR,
    SNtriggered,
    EPCHandoverRestrictionListContainer,
    AdditionalRRMPriorityIndex,
    RequestedFastMCGRecoveryViaSRB3,
    AvailableFastMCGRecoveryViaSRB3,
    RequestedFastMCGRecoveryViaSRB3Release,
    ReleaseFastMCGRecoveryViaSRB3,
    FastMCGRecovery,
    PartialListIndicator,
    MaximumCellListSize,
    MessageOversizeNotification,
    TNLConfigurationInfo,
    TNLA-To-Add-List,
    TNLA-To-Update-List,
    TNLA-To-Remove-List,
    TNLA-Setup-List,
    TNLA-Failed-To-Setup-List,
    RAN-UE-NGAP-ID,
    CHOinformation-REQ,
    CHOinformation-ACK,
    CHOinformation-AddReq,
    CHOinformation-ModReq,
    DAPSRequestInfo,
    DAPSResponseInfo,
    CandidateCellsToBeCancelledList,
    CHO-DC-EarlyDataForwarding,
    CHO-DC-Indicator,
    Ethernet-Type,
    NRV2XServicesAuthorized,
    NRUESidelinkAggregateMaximumBitRate,
    PC5QoSParameters,
    TargetCellInNGRAN,
    Measurement-ID-ENDC,
    Registration-Request-ENDC,
    ReportCharacteristics-ENDC,
    NRRadioResourceStatus,
    TNLCapacityIndicator,
    NRCompositeAvailableCapacityGroup,
    SSBIndex,
    TDDULDLConfigurationCommonNR,
    NRCarrierList,
    SSB-PositionsInBurst,
    NRCellPRACHConfig,
    NBIoT-RLF-Report-Container,
    PrivacyIndicator,
    UERadioCapabilityID,
    CSI-RSTransmissionIndication,
    IABNodeIndication,
    F1CTrafficContainer,
    IntendedTDD-DL-ULConfiguration-NR,
    UERadioCapability,
    SFN-Offset,
    IMSvoiceEPSfallbackfrom5G,
    Global-RAN-NODE-ID,
    DirectForwardingPathAvailability,
    NRRAReport,
    SCG-UE-HistoryInformation,
    PSCellHistoryInformationRetrieve,

    PSCell-UE-HistoryInformation,
    PSCellChangeHistory,
    MeasurementResultforNRCellsPossiblyAggregated,
    SCGActivationStatus,
    SCGActivationRequest,
    CPAinformation-REQ,
    CPAinformation-REQ-ACK,
    CPAinformation-MOD,
    CPAinformation-MOD-ACK,
    CPACinformation-REQD,
    CPCinformation-REQD,
    CPCinformation-CONF,
    CPCinformation-NOTIFY,
    CPCupdate-MOD,
    Additional-Measurement-Timing-Configuration-List,
    ServedCellSpecificInfoReq-NR,
    SecurityIndication,
    SecurityResult,
    TraceCollectionEntityIPAddress,
    SCGreconfigNotification,
    AdditionalListofForwardingGTPTunnelEndpoint,
    RaReportIndicationList,
    IABAuthorized




FROM X2AP-IEs

    PrivateIE-Container{},
    ProtocolExtensionContainer{},
    ProtocolIE-Container{},
    ProtocolIE-ContainerList{},
    ProtocolIE-ContainerPair{},
    ProtocolIE-ContainerPairList{},
    ProtocolIE-Single-Container{},
    X2AP-PRIVATE-IES,
    X2AP-PROTOCOL-EXTENSION,
    X2AP-PROTOCOL-IES,
    X2AP-PROTOCOL-IES-PAIR
FROM X2AP-Containers

    id-ABSInformation,
    id-ActivatedCellList,
    id-BearerType,
    id-Cause,
    id-CellInformation,
    id-CellInformation-Item,
    id-CellMeasurementResult,
    id-CellMeasurementResult-NR-ENDC,
    id-CellMeasurementResult-Item,
    id-CellMeasurementResult-NR-ENDC-Item,
    id-CellMeasurementResult-E-UTRA-ENDC,
    id-CellMeasurementResult-E-UTRA-ENDC-Item,
    id-CellToReport,
    id-CellToReport-E-UTRA-ENDC,
    id-CellToReport-NR-ENDC,
    id-CellToReport-Item,
    id-CellToReport-E-UTRA-ENDC-Item,
    id-CellToReport-NR-ENDC-Item,
    id-CompositeAvailableCapacityGroup,
    id-AerialUEsubscriptionInformation,
    id-CriticalityDiagnostics,
    id-DeactivationIndication,
    id-DynamicDLTransmissionInformation,
    id-E-RABs-Admitted-Item,
    id-E-RABs-Admitted-List,
    id-E-RABs-NotAdmitted-List,
    id-E-RABs-SubjectToStatusTransfer-List,
    id-E-RABs-SubjectToStatusTransfer-Item,
    id-E-RABs-ToBeSetup-Item,
    id-GlobalENB-ID,
    id-GUGroupIDList,
    id-GUGroupIDToAddList,
    id-GUGroupIDToDeleteList,
    id-GUMMEI-ID,
    id-Masked-IMEISV,
    id-IMSvoiceEPSfallbackfrom5G,
    id-InvokeIndication,
    id-New-eNB-UE-X2AP-ID,
    id-Old-eNB-UE-X2AP-ID,
    id-Registration-Request,
    id-ReportingPeriodicity,
    id-RLC-Status,
    id-ServedCells,
    id-ServedCellsToActivate,
    id-ServedCellsToAdd,
    id-ServedCellsToModify,
    id-ServedCellsToDelete,
    id-SRVCCOperationPossible,
    id-TargetCell-ID,
    id-TargeteNBtoSource-eNBTransparentContainer,
    id-TimeToWait,
    id-TraceActivation,
    id-UE-ContextInformation,
    id-UE-HistoryInformation,
    id-UE-X2AP-ID,
    id-Measurement-ID,
    id-ReportCharacteristics,
    id-ENB1-Measurement-ID,
    id-ENB2-Measurement-ID,
    id-ENB1-Cell-ID,
    id-ENB2-Cell-ID,
    id-ENB2-Proposed-Mobility-Parameters,
    id-ENB1-Mobility-Parameters,
    id-ENB2-Mobility-Parameters-Modification-Range,
    id-FailureCellPCI,
    id-Re-establishmentCellECGI,
    id-FailureCellCRNTI,
    id-ShortMAC-I,
    id-SourceCellECGI,
    id-FailureCellECGI,
    id-HandoverReportType,
    id-UE-RLF-Report-Container,
    id-PartialSuccessIndicator,
    id-MeasurementInitiationResult-List,
    id-MeasurementInitiationResult-Item,
    id-MeasurementFailureCause-Item,
    id-CompleteFailureCauseInformation-List,
    id-CompleteFailureCauseInformation-Item,
    id-CSGMembershipStatus,
    id-CSG-Id,
    id-MDTConfiguration,
    id-ManagementBasedMDTallowed,
    id-ABS-Status,
    id-RRCConnSetupIndicator,
    id-RRCConnReestabIndicator,
    id-TargetCellInUTRAN,
    id-MobilityInformation,
    id-SourceCellCRNTI,
    id-ManagementBasedMDTPLMNList,
    id-ReceiveStatusOfULPDCPSDUsExtended,
    id-ULCOUNTValueExtended,
    id-DLCOUNTValueExtended,
    id-IntendedULDLConfiguration,
    id-ExtendedULInterferenceOverloadInfo,
    id-RNL-Header,
    id-x2APMessage,
    id-UE-HistoryInformationFromTheUE,
    id-ExpectedUEBehaviour,
    id-MeNB-UE-X2AP-ID,
    id-SeNB-UE-X2AP-ID,
    id-UE-SecurityCapabilities,
    id-SeNBSecurityKey,
    id-SeNBUEAggregateMaximumBitRate,
    id-ServingPLMN,
    id-E-RABs-ToBeAdded-List,
    id-E-RABs-ToBeAdded-Item,
    id-MeNBtoSeNBContainer,
    id-E-RABs-Admitted-ToBeAdded-List,
    id-E-RABs-Admitted-ToBeAdded-Item,
    id-SeNBtoMeNBContainer,
    id-ResponseInformationSeNBReconfComp,
    id-UE-ContextInformationSeNBModReq,
    id-E-RABs-ToBeAdded-ModReqItem,
    id-E-RABs-ToBeModified-ModReqItem,
    id-E-RABs-ToBeReleased-ModReqItem,
    id-E-RABs-Admitted-ToBeAdded-ModAckList,
    id-E-RABs-Admitted-ToBeModified-ModAckList,
    id-E-RABs-Admitted-ToBeReleased-ModAckList,
    id-E-RABs-Admitted-ToBeAdded-ModAckItem,
    id-E-RABs-Admitted-ToBeModified-ModAckItem,
    id-E-RABs-Admitted-ToBeReleased-ModAckItem,
    id-SCGChangeIndication,
    id-E-RABs-ToBeReleased-ModReqd,
    id-E-RABs-ToBeReleased-ModReqdItem,
    id-E-RABs-ToBeReleased-List-RelReq,
    id-E-RABs-ToBeReleased-RelReqItem,
    id-E-RABs-ToBeReleased-List-RelConf,
    id-E-RABs-ToBeReleased-RelConfItem,
    id-E-RABs-SubjectToCounterCheck-List,
    id-E-RABs-SubjectToCounterCheckItem,
    id-CoMPInformation,
    id-ReportingPeriodicityRSRPMR,
    id-RSRPMRList,
    id-UE-RLF-Report-Container-for-extended-bands,
    id-ProSeAuthorized,
    id-CoverageModificationList,
    id-ReportingPeriodicityCSIR,
    id-CSIReportList,
    id-ReceiveStatusOfULPDCPSDUsPDCP-SNlength18,
    id-ULCOUNTValuePDCP-SNlength18,
    id-DLCOUNTValuePDCP-SNlength18,
    id-LHN-ID,
    id-Correlation-ID,
    id-SIPTO-Correlation-ID,
    id-UE-ContextReferenceAtSeNB,
    id-UE-ContextReferenceAtWT,
    id-UE-ContextKeptIndicator,
    id-UEs-ToBeReset,
    id-UEs-Admitted-ToBeReset,
    id-WT-UE-ContextKeptIndicator,
    id-New-eNB-UE-X2AP-ID-Extension,
    id-Old-eNB-UE-X2AP-ID-Extension,
    id-MeNB-UE-X2AP-ID-Extension,
    id-SeNB-UE-X2AP-ID-Extension,
    id-SIPTO-BearerDeactivationIndication,
    id-Tunnel-Information-for-BBF,
    id-SIPTO-L-GW-TransportLayerAddress,
    id-GW-TransportLayerAddress,
    id-X2RemovalThreshold,
    id-CellReportingIndicator,
    id-V2XServicesAuthorized,
    id-resumeID,
    id-UE-ContextInformationRetrieve,
    id-E-RABs-ToBeSetupRetrieve-Item,
    id-NewEUTRANCellIdentifier,
    id-MakeBeforeBreakIndicator,
    id-UESidelinkAggregateMaximumBitRate,
    id-uL-GTPtunnelEndpoint,
    id-SgNBSecurityKey,
    id-SgNBUEAggregateMaximumBitRate,
    id-E-RABs-ToBeAdded-SgNBAddReqList,
    id-MeNBtoSgNBContainer,
    id-SgNB-UE-X2AP-ID,
    id-RequestedSplitSRBs,
    id-E-RABs-ToBeAdded-SgNBAddReq-Item,
    id-E-RABs-Admitted-ToBeAdded-SgNBAddReqAckList,
    id-SgNBtoMeNBContainer,
    id-AdmittedSplitSRBs,
    id-E-RABs-Admitted-ToBeAdded-SgNBAddReqAck-Item,
    id-ResponseInformationSgNBReconfComp,
    id-UE-ContextInformation-SgNBModReq,
    id-E-RABs-ToBeAdded-SgNBModReq-Item,
    id-E-RABs-ToBeModified-SgNBModReq-Item,
    id-E-RABs-ToBeReleased-SgNBModReq-Item,
    id-E-RABs-Admitted-ToBeAdded-SgNBModAckList,
    id-E-RABs-Admitted-ToBeModified-SgNBModAckList,
    id-E-RABs-Admitted-ToBeReleased-SgNBModAckList,
    id-E-RABs-Admitted-ToBeAdded-SgNBModAck-Item,
    id-E-RABs-Admitted-ToBeModified-SgNBModAck-Item,
    id-E-RABs-Admitted-ToBeReleased-SgNBModAck-Item,
    id-E-RABs-Admitted-ToBeReleased-SgNBRelReqAckList,
    id-E-RABs-Admitted-ToBeReleased-SgNBRelReqAck-Item,
    id-E-RABs-ToBeReleased-SgNBModReqdList,
    id-E-RABs-ToBeModified-SgNBModReqdList,
    id-E-RABs-ToBeReleased-SgNBModReqd-Item,
    id-E-RABs-ToBeModified-SgNBModReqd-Item,
    id-E-RABs-ToBeReleased-SgNBChaConfList,
    id-E-RABs-ToBeReleased-SgNBChaConf-Item,
    id-E-RABs-ToBeReleased-SgNBRelReqList,
    id-E-RABs-ToBeReleased-SgNBRelReq-Item,
    id-E-RABs-ToBeReleased-SgNBRelConfList,
    id-E-RABs-ToBeReleased-SgNBRelConf-Item,
    id-E-RABs-ToBeReleased-SgNBRelReqdList,
    id-E-RABs-ToBeReleased-SgNBRelReqd-Item,
    id-E-RABs-SubjectToSgNBCounterCheck-List,
    id-E-RABs-SubjectToSgNBCounterCheck-Item,
    id-Target-SgNB-ID,
    id-RRCContainer,
    id-SRBType,
    id-HandoverRestrictionList,
    id-SCGConfigurationQuery,
    id-SplitSRB,
    id-NRUeReport,
    id-InitiatingNodeType-EndcX2Setup,
    id-InitiatingNodeType-EndcConfigUpdate,
    id-RespondingNodeType-EndcX2Setup,
    id-RespondingNodeType-EndcConfigUpdate,
    id-NRUESecurityCapabilities,
    id-PDCPChangeIndication,
    id-ServedEUTRAcellsENDCX2ManagementList,
    id-ServedEUTRAcellsToModifyListENDCConfUpd,
    id-ServedEUTRAcellsToDeleteListENDCConfUpd,
    id-ServedNRcellsToModifyListENDCConfUpd,
    id-ServedNRcellsToDeleteListENDCConfUpd,
    id-CellAssistanceInformation,
    id-Globalen-gNB-ID,
    id-ServedNRcellsENDCX2ManagementList,
    id-Old-SgNB-UE-X2AP-ID,
    id-UE-ContextReferenceAtSgNB,
    id-SecondaryRATUsageReportList,
    id-ActivationID,
    id-ServedNRCellsToActivate,
    id-ActivatedNRCellList,
    id-MeNBResourceCoordinationInformation,
    id-SgNBResourceCoordinationInformation,
    id-UEAppLayerMeasConfig,
    id-SelectedPLMN,
    id-SubscriberProfileIDforRFP,
    id-InitiatingNodeType-EutranrCellResourceCoordination,
    id-RespondingNodeType-EutranrCellResourceCoordination,
    id-DataTrafficResourceIndication,
    id-SpectrumSharingGroupID,
    id-ListofEUTRACellsinEUTRACoordinationReq,
    id-ListofEUTRACellsinEUTRACoordinationResp,
    id-ListofEUTRACellsinNRCoordinationReq,
    id-ListofNRCellsinNRCoordinationReq,
    id-ListofNRCellsinNRCoordinationResp,
    id-RRCConfigIndication,
    id-SGNB-Addition-Trigger-Ind,
    id-RequestedSplitSRBsrelease,
    id-AdmittedSplitSRBsrelease,
    id-E-RABs-AdmittedToBeModified-SgNBModConfList,
    id-E-RABs-AdmittedToBeModified-SgNBModConf-Item,
    id-UEContextLevelUserPlaneActivity,
    id-ERABActivityNotifyItemList,
    id-MeNBCell-ID,
    id-InitiatingNodeType-EndcX2Removal,
    id-RespondingNodeType-EndcX2Removal,
    id-uLpDCPSnLength,
    id-dL-Forwarding,
    id-E-RABs-DataForwardingAddress-List,
    id-E-RABs-DataForwardingAddress-Item,
    id-Subscription-Based-UE-DifferentiationInfo,
    id-RLCMode-transferred,
    id-dLPDCPSnLength,
    id-secondarysgNBDLGTPTEIDatPDCP,
    id-secondarymeNBULGTPTEIDatPDCP,
    id-lCID,
    id-duplicationActivation,
    id-GNBOverloadInformation,
    id-new-drb-ID-req,
    id-NRNeighbourInfoToModify,
    id-DesiredActNotificationLevel,
    id-LocationInformationSgNB,
    id-LocationInformationSgNBReporting,
    id-endcSONConfigurationTransfer,
    id-EUTRANTraceID,
    id-additionalPLMNs-Item,
    id-InterfaceInstanceIndication,
    id-BPLMN-ID-Info-NR,
    id-SNtriggered,
    id-EPCHandoverRestrictionListContainer,
    id-ERABs-transferred-to-MeNB,
    id-AdditionalRRMPriorityIndex,
    id-LowerLayerPresenceStatusChange,
    id-FastMCGRecovery-SN-to-MN,
    id-FastMCGRecovery-MN-to-SN,
    id-RequestedFastMCGRecoveryViaSRB3,
    id-AvailableFastMCGRecoveryViaSRB3,
    id-RequestedFastMCGRecoveryViaSRB3Release,
    id-ReleaseFastMCGRecoveryViaSRB3,
    id-PartialListIndicator,
    id-MaximumCellListSize,
    id-MessageOversizeNotification,
    id-CellandCapacityAssistInfo,
    id-TNLConfigurationInfo,
    id-TNLA-To-Add-List,
    id-TNLA-To-Update-List,
    id-TNLA-To-Remove-List,
    id-TNLA-Setup-List,
    id-TNLA-Failed-To-Setup-List,
    id-UEContextReferenceatSourceNGRAN,
    id-CHOinformation-REQ,
    id-CHOinformation-ACK,
    id-CHOinformation-AddReq,
    id-CHOinformation-ModReq,
    id-DAPSRequestInfo,
    id-RequestedTargetCellID,
    id-CandidateCellsToBeCancelledList,
    id-DAPSResponseInfo,
    id-ProcedureStage,
    id-CHO-DC-EarlyDataForwarding,
    id-CHO-DC-Indicator,
    id-Ethernet-Type,
    id-NRV2XServicesAuthorized,
    id-NRUESidelinkAggregateMaximumBitRate,
    id-PC5QoSParameters,
    id-TargetCellInNGRAN,
    id-E-UTRAN-Node1-Measurement-ID,
    id-E-UTRAN-Node2-Measurement-ID,
    id-TDDULDLConfigurationCommonNR,
    id-CarrierList,
    id-ULCarrierList,
    id-SSB-PositionsInBurst,
    id-NRCellPRACHConfig,
    id-NBIoT-RLF-Report-Container,
    id-MDTConfigurationNR,
    id-PrivacyIndicator,
    id-TraceCollectionEntityIPAddress,
    id-UERadioCapabilityID,
    id-CSI-RSTransmissionIndication,
    id-DLCarrierList,
    id-IABNodeIndication,
    id-F1CTrafficContainer,
    id-IntendedTDD-DL-ULConfiguration-NR,
    id-UERadioCapability,
    id-SFN-Offset,
    id-DirectForwardingPathAvailability,
    id-sourceNG-RAN-node-id,
    id-SourceDLForwardingIPAddress,
    id-SourceNodeDLForwardingIPAddress,
    id-NRRAReport,
    id-SCG-UE-HistoryInformation,
    id-PSCellHistoryInformationRetrieve,
    id-MeasurementResultforNRCellsPossiblyAggregated,
    id-PSCellChangeHistory,
    id-SCGActivationStatus,
    id-SCGActivationRequest,
    id-CPAinformation-REQ,
    id-CPAinformation-REQ-ACK,
    id-CPAinformation-MOD,
    id-CPAinformation-MOD-ACK,
    id-CPACinformation-REQD,
    id-CPCinformation-REQD,
    id-CPCinformation-CONF,
    id-CPCinformation-NOTIFY,
    id-CPCupdate-MOD,
    id-Additional-Measurement-Timing-Configuration-List,
    id-ServedCellSpecificInfoReq-NR,
    id-SecurityIndication,
    id-SecurityResult,
    id-SCGreconfigNotification,
    id-AdditionalListofForwardingGTPTunnelEndpoint,
    id-RaReportIndicationList,
    id-IABAuthorized,
    maxCellineNB,
    maxnoofBearers,
    maxnoofPDCP-SN,
    maxFailedMeasObjects,
    maxnoofCellIDforMDT,
    maxnoofTAforMDT,
    maxCellinengNB,
    maxnoofCellIDforQMC,
    maxnoofTAforQMC,
    maxnoofPLMNforQMC,
    maxnoofProtectedResourcePatterns,
    maxnoNRcellsSpectrumSharingWithE-UTRA,
    maxnoofNrCellBands,
    maxnoofSSBAreas

FROM X2AP-Constants;

-- **************************************************************
--
-- HANDOVER REQUEST
--
-- **************************************************************

HandoverRequest ::= SEQUENCE {
    protocolIEs         ProtocolIE-Container    {{HandoverRequest-IEs}},
    ...
}

HandoverRequest-IEs X2AP-PROTOCOL-IES ::= {
    { ID id-Old-eNB-UE-X2AP-ID                          CRITICALITY reject  TYPE UE-X2AP-ID                                             PRESENCE mandatory}|
    { ID id-Cause                                       CRITICALITY ignore  TYPE Cause                                                  PRESENCE mandatory}|
    { ID id-TargetCell-ID                               CRITICALITY reject  TYPE ECGI                                                   PRESENCE mandatory}|
    { ID id-GUMMEI-ID                                   CRITICALITY reject  TYPE GUMMEI                                                 PRESENCE mandatory}|
    { ID id-UE-ContextInformation                       CRITICALITY reject  TYPE UE-ContextInformation                              PRESENCE mandatory}|
    { ID id-UE-HistoryInformation                       CRITICALITY ignore  TYPE UE-HistoryInformation                              PRESENCE mandatory}|
    { ID id-TraceActivation                             CRITICALITY ignore  TYPE TraceActivation                                        PRESENCE optional}|
    { ID id-SRVCCOperationPossible                      CRITICALITY ignore  TYPE SRVCCOperationPossible                             PRESENCE optional}|
    { ID id-CSGMembershipStatus                         CRITICALITY reject  TYPE CSGMembershipStatus                                    PRESENCE optional}|
    { ID id-MobilityInformation                         CRITICALITY ignore  TYPE MobilityInformation                                    PRESENCE optional}|
    { ID id-Masked-IMEISV                               CRITICALITY ignore  TYPE Masked-IMEISV                                          PRESENCE optional}|
    { ID id-UE-HistoryInformationFromTheUE              CRITICALITY ignore  TYPE UE-HistoryInformationFromTheUE                 PRESENCE optional}|
    { ID id-ExpectedUEBehaviour                         CRITICALITY ignore  TYPE ExpectedUEBehaviour                                    PRESENCE optional}|
    { ID id-ProSeAuthorized                             CRITICALITY ignore  TYPE ProSeAuthorized                                        PRESENCE optional}|
    { ID id-UE-ContextReferenceAtSeNB                   CRITICALITY ignore  TYPE UE-ContextReferenceAtSeNB                          PRESENCE optional}|
    { ID id-Old-eNB-UE-X2AP-ID-Extension                CRITICALITY reject  TYPE UE-X2AP-ID-Extension                               PRESENCE optional}|
    { ID id-V2XServicesAuthorized                       CRITICALITY ignore  TYPE V2XServicesAuthorized                              PRESENCE optional}|
    { ID id-UE-ContextReferenceAtWT                     CRITICALITY ignore  TYPE UE-ContextReferenceAtWT                            PRESENCE optional}|
    { ID id-NRUESecurityCapabilities                    CRITICALITY ignore  TYPE NRUESecurityCapabilities                           PRESENCE optional}|
    { ID id-UE-ContextReferenceAtSgNB                   CRITICALITY ignore  TYPE UE-ContextReferenceAtSgNB                          PRESENCE optional}|
    { ID id-AerialUEsubscriptionInformation             CRITICALITY ignore  TYPE AerialUEsubscriptionInformation                    PRESENCE optional}|
    { ID id-Subscription-Based-UE-DifferentiationInfo   CRITICALITY ignore  TYPE Subscription-Based-UE-DifferentiationInfo  PRESENCE optional}|
    { ID id-CHOinformation-REQ                          CRITICALITY reject  TYPE CHOinformation-REQ                                 PRESENCE optional}|
    { ID id-NRV2XServicesAuthorized                     CRITICALITY ignore  TYPE NRV2XServicesAuthorized                            PRESENCE optional}|
    { ID id-PC5QoSParameters                            CRITICALITY ignore  TYPE PC5QoSParameters                                       PRESENCE optional }|
    { ID id-IABNodeIndication                           CRITICALITY reject  TYPE IABNodeIndication                                  PRESENCE optional},
    ...
}

UE-ContextInformation ::= SEQUENCE {
    mME-UE-S1AP-ID                      UE-S1AP-ID,
    uESecurityCapabilities              UESecurityCapabilities,
    aS-SecurityInformation              AS-SecurityInformation,
    uEaggregateMaximumBitRate           UEAggregateMaximumBitRate,
    subscriberProfileIDforRFP           SubscriberProfileIDforRFP       OPTIONAL,
    e-RABs-ToBeSetup-List               E-RABs-ToBeSetup-List,
    rRC-Context                         RRC-Context,
    handoverRestrictionList             HandoverRestrictionList     OPTIONAL,
    locationReportingInformation        LocationReportingInformation    OPTIONAL,
    iE-Extensions                       ProtocolExtensionContainer { {UE-ContextInformation-ExtIEs} } OPTIONAL,
    ...
}

UE-ContextInformation-ExtIEs X2AP-PROTOCOL-EXTENSION ::= {
{ ID id-ManagementBasedMDTallowed           CRITICALITY ignore  EXTENSION ManagementBasedMDTallowed                 PRESENCE optional }|
{ ID id-ManagementBasedMDTPLMNList          CRITICALITY ignore  EXTENSION MDTPLMNList                                   PRESENCE optional }|
{ ID id-UESidelinkAggregateMaximumBitRate   CRITICALITY ignore  EXTENSION UESidelinkAggregateMaximumBitRate     PRESENCE optional }|
{ ID id-EPCHandoverRestrictionListContainer CRITICALITY ignore  EXTENSION EPCHandoverRestrictionListContainer       PRESENCE optional }|
{ ID id-AdditionalRRMPriorityIndex          CRITICALITY ignore  EXTENSION AdditionalRRMPriorityIndex                    PRESENCE optional}|
{ ID id-NRUESidelinkAggregateMaximumBitRate CRITICALITY ignore  EXTENSION NRUESidelinkAggregateMaximumBitRate       PRESENCE optional}|
{ ID id-UERadioCapabilityID                 CRITICALITY reject  EXTENSION UERadioCapabilityID                           PRESENCE optional }|
{ ID id-IMSvoiceEPSfallbackfrom5G           CRITICALITY ignore  EXTENSION IMSvoiceEPSfallbackfrom5G                 PRESENCE optional},
    ...
}

E-RABs-ToBeSetup-List ::= SEQUENCE (SIZE(1..maxnoofBearers)) OF ProtocolIE-Single-Container { {E-RABs-ToBeSetup-ItemIEs} }

E-RABs-ToBeSetup-ItemIEs    X2AP-PROTOCOL-IES ::= {
    { ID id-E-RABs-ToBeSetup-Item    CRITICALITY ignore     TYPE E-RABs-ToBeSetup-Item  PRESENCE mandatory },
    ...
}

E-RABs-ToBeSetup-Item ::= SEQUENCE {
    e-RAB-ID                    E-RAB-ID,
    e-RAB-Level-QoS-Parameters      E-RAB-Level-QoS-Parameters,
    dL-Forwarding                   DL-Forwarding                                                   OPTIONAL,
    uL-GTPtunnelEndpoint            GTPtunnelEndpoint,
    iE-Extensions                   ProtocolExtensionContainer { {E-RABs-ToBeSetup-ItemExtIEs} } OPTIONAL,
    ...
}

E-RABs-ToBeSetup-ItemExtIEs X2AP-PROTOCOL-EXTENSION ::= {
    { ID id-BearerType      CRITICALITY reject  EXTENSION BearerType        PRESENCE optional}|
    { ID id-DAPSRequestInfo     CRITICALITY ignore  EXTENSION DAPSRequestInfo           PRESENCE optional}|
    { ID id-Ethernet-Type   CRITICALITY ignore  EXTENSION Ethernet-Type     PRESENCE optional}|
    { ID id-SourceDLForwardingIPAddress         CRITICALITY ignore  EXTENSION TransportLayerAddress     PRESENCE optional}|
    { ID id-SecurityIndication  CRITICALITY reject  EXTENSION SecurityIndication                PRESENCE optional},
    ...
}

MobilityInformation ::= BIT STRING (SIZE(32))

SourceDLForwardingIPAddress ::= BIT STRING (SIZE(1..160, ...))


UE-ContextReferenceAtSeNB ::= SEQUENCE {
    source-GlobalSeNB-ID        GlobalENB-ID,
    seNB-UE-X2AP-ID             UE-X2AP-ID,
    seNB-UE-X2AP-ID-Extension   UE-X2AP-ID-Extension,
    iE-Extensions               ProtocolExtensionContainer { {UE-ContextReferenceAtSeNB-ItemExtIEs} } OPTIONAL,
    ...
}

UE-ContextReferenceAtSeNB-ItemExtIEs X2AP-PROTOCOL-EXTENSION ::= {
    ...
}

UE-ContextReferenceAtWT ::= SEQUENCE {
    wTID                    WTID,
    wT-UE-XwAP-ID           WT-UE-XwAP-ID,
    iE-Extensions           ProtocolExtensionContainer { {UE-ContextReferenceAtWT-ItemExtIEs} } OPTIONAL,
    ...
}

UE-ContextReferenceAtWT-ItemExtIEs  X2AP-PROTOCOL-EXTENSION ::= {
    ...
}

UE-ContextReferenceAtSgNB ::= SEQUENCE {
    source-GlobalSgNB-ID            GlobalGNB-ID,
    sgNB-UE-X2AP-ID             SgNB-UE-X2AP-ID,
    iE-Extensions               ProtocolExtensionContainer { {UE-ContextReferenceAtSgNB-ItemExtIEs} } OPTIONAL,
    ...
}

UE-ContextReferenceAtSgNB-ItemExtIEs X2AP-PROTOCOL-EXTENSION ::= {
    ...
}

-- **************************************************************
--
-- HANDOVER REQUEST ACKNOWLEDGE
--
-- **************************************************************

HandoverRequestAcknowledge ::= SEQUENCE {
    protocolIEs     ProtocolIE-Container    {{HandoverRequestAcknowledge-IEs}},
    ...
}

HandoverRequestAcknowledge-IEs X2AP-PROTOCOL-IES ::= {
    { ID id-Old-eNB-UE-X2AP-ID                          CRITICALITY ignore  TYPE UE-X2AP-ID     PRESENCE mandatory}|
    { ID id-New-eNB-UE-X2AP-ID                          CRITICALITY ignore  TYPE UE-X2AP-ID     PRESENCE mandatory}|
    { ID id-E-RABs-Admitted-List                        CRITICALITY ignore  TYPE E-RABs-Admitted-List   PRESENCE mandatory}|
    { ID id-E-RABs-NotAdmitted-List                     CRITICALITY ignore  TYPE E-RAB-List     PRESENCE optional}|
    { ID id-TargeteNBtoSource-eNBTransparentContainer   CRITICALITY ignore  TYPE TargeteNBtoSource-eNBTransparentContainer  PRESENCE mandatory}|
    { ID id-CriticalityDiagnostics                      CRITICALITY ignore  TYPE CriticalityDiagnostics PRESENCE optional}|
    { ID id-UE-ContextKeptIndicator                     CRITICALITY ignore  TYPE UE-ContextKeptIndicator    PRESENCE optional}|
    { ID id-SeNB-UE-X2AP-ID-Extension                   CRITICALITY ignore  TYPE UE-X2AP-ID-Extension   PRESENCE optional}-- The id-SeNB-UE-X2AP-ID-Extension shall not be sent and shall be ignored, if received.--|
    { ID id-Old-eNB-UE-X2AP-ID-Extension                CRITICALITY ignore  TYPE UE-X2AP-ID-Extension   PRESENCE optional}|
    { ID id-New-eNB-UE-X2AP-ID-Extension                CRITICALITY reject  TYPE UE-X2AP-ID-Extension   PRESENCE optional}|
    { ID id-WT-UE-ContextKeptIndicator                  CRITICALITY ignore  TYPE UE-ContextKeptIndicator    PRESENCE optional}|
    { ID id-ERABs-transferred-to-MeNB                   CRITICALITY ignore  TYPE E-RAB-List         PRESENCE optional}|
    { ID id-CHOinformation-ACK                          CRITICALITY ignore  TYPE CHOinformation-ACK                                 PRESENCE optional},
    ...
}

E-RABs-Admitted-List        ::= SEQUENCE (SIZE (1..maxnoofBearers)) OF ProtocolIE-Single-Container { {E-RABs-Admitted-ItemIEs} }

E-RABs-Admitted-ItemIEs X2AP-PROTOCOL-IES ::= {
    { ID id-E-RABs-Admitted-Item    CRITICALITY ignore  TYPE E-RABs-Admitted-Item   PRESENCE mandatory  }
}

E-RABs-Admitted-Item ::= SEQUENCE {
    e-RAB-ID                    E-RAB-ID,
    uL-GTP-TunnelEndpoint           GTPtunnelEndpoint   OPTIONAL,
    dL-GTP-TunnelEndpoint           GTPtunnelEndpoint   OPTIONAL,
    iE-Extensions                   ProtocolExtensionContainer { {E-RABs-Admitted-Item-ExtIEs} }    OPTIONAL,
    ...
}

E-RABs-Admitted-Item-ExtIEs X2AP-PROTOCOL-EXTENSION ::= {
    { ID id-DAPSResponseInfo                CRITICALITY reject  EXTENSION DAPSResponseInfo          PRESENCE optional},
    ...
}

-- **************************************************************
--
-- HANDOVER PREPARATION FAILURE
--
-- **************************************************************

HandoverPreparationFailure ::= SEQUENCE {
    protocolIEs     ProtocolIE-Container    {{HandoverPreparationFailure-IEs}},
    ...
}

HandoverPreparationFailure-IEs X2AP-PROTOCOL-IES ::= {
    { ID id-Old-eNB-UE-X2AP-ID              CRITICALITY ignore  TYPE UE-X2AP-ID                 PRESENCE mandatory}|
    { ID id-Cause                           CRITICALITY ignore  TYPE Cause                      PRESENCE mandatory}|
    { ID id-CriticalityDiagnostics          CRITICALITY ignore  TYPE CriticalityDiagnostics     PRESENCE optional}|
    { ID id-Old-eNB-UE-X2AP-ID-Extension    CRITICALITY ignore  TYPE UE-X2AP-ID-Extension       PRESENCE optional}|
    { ID id-RequestedTargetCellID           CRITICALITY reject  TYPE ECGI                       PRESENCE optional},
    ...
}

-- **************************************************************
--
-- HANDOVER REPORT
--
-- **************************************************************

HandoverReport ::= SEQUENCE {
    protocolIEs     ProtocolIE-Container    {{HandoverReport-IEs}},
    ...
}

HandoverReport-IEs X2AP-PROTOCOL-IES ::= {
    { ID id-HandoverReportType                          CRITICALITY ignore  TYPE HandoverReportType                                 PRESENCE mandatory}|
    { ID id-Cause                                       CRITICALITY ignore  TYPE Cause                                                  PRESENCE mandatory}|
    { ID id-SourceCellECGI                              CRITICALITY ignore  TYPE ECGI                                                   PRESENCE mandatory}|
    { ID id-FailureCellECGI                             CRITICALITY ignore  TYPE ECGI                                                   PRESENCE mandatory}|
    { ID id-Re-establishmentCellECGI                    CRITICALITY ignore  TYPE ECGI                                                   PRESENCE conditional} -- The IE shall be present if the Handover Report Type IE is set to “HO to Wrong Cell” -- |
    { ID id-TargetCellInUTRAN                           CRITICALITY ignore  TYPE TargetCellInUTRAN                                  PRESENCE conditional} -- The IE shall be present if the Handover Report Type IE is set to "InterRAT ping-pong" --|
    { ID id-SourceCellCRNTI                             CRITICALITY ignore  TYPE CRNTI                                                  PRESENCE optional}|
    { ID id-MobilityInformation                         CRITICALITY ignore  TYPE MobilityInformation                                    PRESENCE optional}|
    { ID id-UE-RLF-Report-Container                     CRITICALITY ignore  TYPE UE-RLF-Report-Container                            PRESENCE optional}|
    { ID id-UE-RLF-Report-Container-for-extended-bands  CRITICALITY ignore  TYPE UE-RLF-Report-Container-for-extended-bands PRESENCE optional}|
    { ID id-TargetCellInNGRAN                           CRITICALITY ignore  TYPE TargetCellInNGRAN                                  PRESENCE conditional} -- The IE shall be present if the Handover Report Type IE is set to "interSystemPingpong" --,
    ...
}

-- **************************************************************
--
-- EARLY STATUS TRANSFER
--
-- **************************************************************

EarlyStatusTransfer ::= SEQUENCE {
    protocolIEs         ProtocolIE-Container    {{ EarlyStatusTransfer-IEs}},
    ...
}

EarlyStatusTransfer-IEs X2AP-PROTOCOL-IES ::= {
    { ID id-Old-eNB-UE-X2AP-ID                  CRITICALITY reject      TYPE UE-X2AP-ID                                 PRESENCE mandatory}|
    { ID id-New-eNB-UE-X2AP-ID                  CRITICALITY reject      TYPE UE-X2AP-ID                                 PRESENCE mandatory}|
    { ID id-Old-eNB-UE-X2AP-ID-Extension        CRITICALITY reject      TYPE UE-X2AP-ID-Extension                       PRESENCE optional}|
    { ID id-New-eNB-UE-X2AP-ID-Extension        CRITICALITY reject      TYPE UE-X2AP-ID-Extension                       PRESENCE optional}|
    { ID id-ProcedureStage                      CRITICALITY reject      TYPE ProcedureStageChoice                       PRESENCE mandatory}|
    { ID id-SgNB-UE-X2AP-ID                     CRITICALITY ignore      TYPE SgNB-UE-X2AP-ID                            PRESENCE optional},
    ...
}

ProcedureStageChoice ::= CHOICE {
    first-dl-count                      FirstDLCount,
    dl-discarding                       DLDiscarding,
    choice-extension                    ProtocolIE-Single-Container { {ProcedureStageChoice-ExtIEs} }
}

ProcedureStageChoice-ExtIEs X2AP-PROTOCOL-IES ::= {
    ...
}

FirstDLCount ::= SEQUENCE {
    e-RABsSubjectToEarlyStatusTransfer      E-RABsSubjectToEarlyStatusTransfer-List,
    iE-Extension                                ProtocolExtensionContainer { {FirstDLCount-ExtIEs} }    OPTIONAL,
    ...
}

FirstDLCount-ExtIEs X2AP-PROTOCOL-EXTENSION ::= {
    ...
}

DLDiscarding ::= SEQUENCE {
    e-RABsSubjectToDLDiscarding-List            E-RABsSubjectToDLDiscarding-List,
    iE-Extension                                ProtocolExtensionContainer { {DLDiscarding-ExtIEs} }    OPTIONAL,
    ...
}

DLDiscarding-ExtIEs X2AP-PROTOCOL-EXTENSION ::= {
    ...
}
-- **************************************************************
--
-- SN STATUS TRANSFER
--
-- **************************************************************

SNStatusTransfer ::= SEQUENCE {
    protocolIEs     ProtocolIE-Container    {{SNStatusTransfer-IEs}},
    ...
}

SNStatusTransfer-IEs X2AP-PROTOCOL-IES ::= {
    { ID id-Old-eNB-UE-X2AP-ID                      CRITICALITY reject  TYPE UE-X2AP-ID                                     PRESENCE mandatory}|
    { ID id-New-eNB-UE-X2AP-ID                      CRITICALITY reject  TYPE UE-X2AP-ID                                     PRESENCE mandatory}|
    { ID id-E-RABs-SubjectToStatusTransfer-List     CRITICALITY ignore  TYPE E-RABs-SubjectToStatusTransfer-List        PRESENCE mandatory}|
    { ID id-Old-eNB-UE-X2AP-ID-Extension            CRITICALITY reject  TYPE UE-X2AP-ID-Extension                           PRESENCE optional}|
    { ID id-New-eNB-UE-X2AP-ID-Extension            CRITICALITY reject  TYPE UE-X2AP-ID-Extension                           PRESENCE optional}|
    { ID id-SgNB-UE-X2AP-ID                         CRITICALITY ignore  TYPE SgNB-UE-X2AP-ID                                PRESENCE optional},
    ...
}

E-RABs-SubjectToStatusTransfer-List ::= SEQUENCE (SIZE (1..maxnoofBearers)) OF ProtocolIE-Single-Container { {E-RABs-SubjectToStatusTransfer-ItemIEs} }

E-RABs-SubjectToStatusTransfer-ItemIEs X2AP-PROTOCOL-IES ::= {
    { ID id-E-RABs-SubjectToStatusTransfer-Item CRITICALITY ignore  TYPE E-RABs-SubjectToStatusTransfer-Item    PRESENCE mandatory  }
}

E-RABs-SubjectToStatusTransfer-Item ::= SEQUENCE {
    e-RAB-ID                                E-RAB-ID,

    receiveStatusofULPDCPSDUs               ReceiveStatusofULPDCPSDUs           OPTIONAL,
    uL-COUNTvalue                   COUNTvalue,
    dL-COUNTvalue                   COUNTvalue,
    iE-Extensions                           ProtocolExtensionContainer { {E-RABs-SubjectToStatusTransfer-ItemExtIEs} } OPTIONAL,
    ...
}

E-RABs-SubjectToStatusTransfer-ItemExtIEs X2AP-PROTOCOL-EXTENSION ::= {
    { ID id-ReceiveStatusOfULPDCPSDUsExtended           CRITICALITY ignore  EXTENSION ReceiveStatusOfULPDCPSDUsExtended         PRESENCE optional}|
    { ID id-ULCOUNTValueExtended                        CRITICALITY ignore  EXTENSION COUNTValueExtended                                PRESENCE optional}|
    { ID id-DLCOUNTValueExtended                        CRITICALITY ignore  EXTENSION COUNTValueExtended                                PRESENCE optional}|
    { ID id-ReceiveStatusOfULPDCPSDUsPDCP-SNlength18    CRITICALITY ignore  EXTENSION ReceiveStatusOfULPDCPSDUsPDCP-SNlength18  PRESENCE optional}|
    { ID id-ULCOUNTValuePDCP-SNlength18                 CRITICALITY ignore  EXTENSION COUNTvaluePDCP-SNlength18                     PRESENCE optional}|
    { ID id-DLCOUNTValuePDCP-SNlength18                 CRITICALITY ignore  EXTENSION COUNTvaluePDCP-SNlength18                     PRESENCE optional},
    ...
}

-- **************************************************************
--
-- UE CONTEXT RELEASE
--
-- **************************************************************

UEContextRelease ::= SEQUENCE {
    protocolIEs     ProtocolIE-Container    {{UEContextRelease-IEs}},
    ...
}

UEContextRelease-IEs X2AP-PROTOCOL-IES ::= {
    { ID id-Old-eNB-UE-X2AP-ID                  CRITICALITY reject  TYPE UE-X2AP-ID                                 PRESENCE mandatory}|
    { ID id-New-eNB-UE-X2AP-ID                  CRITICALITY reject  TYPE UE-X2AP-ID                                 PRESENCE mandatory}|
    { ID id-Old-eNB-UE-X2AP-ID-Extension        CRITICALITY reject  TYPE UE-X2AP-ID-Extension                       PRESENCE optional}|
    { ID id-New-eNB-UE-X2AP-ID-Extension        CRITICALITY reject  TYPE UE-X2AP-ID-Extension                       PRESENCE optional}|
    { ID id-SIPTO-BearerDeactivationIndication  CRITICALITY ignore  TYPE SIPTOBearerDeactivationIndication      PRESENCE optional}|
    { ID id-SgNB-UE-X2AP-ID                     CRITICALITY ignore  TYPE SgNB-UE-X2AP-ID                            PRESENCE optional},
    ...
}


-- **************************************************************
--
-- HANDOVER CANCEL
--
-- **************************************************************

HandoverCancel ::= SEQUENCE {
    protocolIEs     ProtocolIE-Container    {{HandoverCancel-IEs}},
    ...
}

HandoverCancel-IEs X2AP-PROTOCOL-IES ::= {
    { ID id-Old-eNB-UE-X2AP-ID                  CRITICALITY reject  TYPE UE-X2AP-ID                                     PRESENCE mandatory}|
    { ID id-New-eNB-UE-X2AP-ID                  CRITICALITY ignore  TYPE UE-X2AP-ID                                     PRESENCE optional}|
    { ID id-Cause                               CRITICALITY ignore  TYPE Cause                                          PRESENCE mandatory}|
    { ID id-Old-eNB-UE-X2AP-ID-Extension            CRITICALITY reject  TYPE UE-X2AP-ID-Extension                       PRESENCE optional}|
    { ID id-New-eNB-UE-X2AP-ID-Extension            CRITICALITY ignore  TYPE UE-X2AP-ID-Extension                       PRESENCE optional}|
    { ID id-CandidateCellsToBeCancelledList     CRITICALITY reject  TYPE CandidateCellsToBeCancelledList            PRESENCE optional},
    ...
}


-- **************************************************************
--
-- HANDOVER SUCCESS
--
-- **************************************************************

HandoverSuccess ::= SEQUENCE {
    protocolIEs     ProtocolIE-Container    {{HandoverSuccess-IEs}},
    ...
}

HandoverSuccess-IEs X2AP-PROTOCOL-IES ::= {
    { ID id-Old-eNB-UE-X2AP-ID                  CRITICALITY reject TYPE UE-X2AP-ID                  PRESENCE mandatory}|
    { ID id-New-eNB-UE-X2AP-ID                  CRITICALITY reject TYPE UE-X2AP-ID                  PRESENCE mandatory}|
    { ID id-Old-eNB-UE-X2AP-ID-Extension        CRITICALITY ignore  TYPE UE-X2AP-ID-Extension       PRESENCE optional}|
    { ID id-New-eNB-UE-X2AP-ID-Extension        CRITICALITY ignore  TYPE UE-X2AP-ID-Extension       PRESENCE optional}|
    { ID id-TargetCell-ID                       CRITICALITY reject  TYPE ECGI                       PRESENCE mandatory},
    ...
}

-- **************************************************************
--
-- CONDITIONAL HANDOVER CANCEL
--
-- **************************************************************

ConditionalHandoverCancel ::= SEQUENCE {
    protocolIEs     ProtocolIE-Container    {{ConditionalHandoverCancel-IEs}},
    ...
}

ConditionalHandoverCancel-IEs X2AP-PROTOCOL-IES ::= {
    { ID id-Old-eNB-UE-X2AP-ID                  CRITICALITY reject  TYPE UE-X2AP-ID                 PRESENCE mandatory}|
    { ID id-New-eNB-UE-X2AP-ID                  CRITICALITY ignore  TYPE UE-X2AP-ID                 PRESENCE optional}|
    { ID id-Cause                               CRITICALITY ignore  TYPE Cause                      PRESENCE mandatory}|
    { ID id-Old-eNB-UE-X2AP-ID-Extension        CRITICALITY reject  TYPE UE-X2AP-ID-Extension       PRESENCE optional}|
    { ID id-New-eNB-UE-X2AP-ID-Extension        CRITICALITY ignore  TYPE UE-X2AP-ID-Extension       PRESENCE optional}|
    { ID id-CandidateCellsToBeCancelledList     CRITICALITY reject  TYPE CandidateCellsToBeCancelledList            PRESENCE optional},
    ...
}

-- **************************************************************
--
-- ERROR INDICATION
--
-- **************************************************************

ErrorIndication ::= SEQUENCE {
    protocolIEs     ProtocolIE-Container    {{ErrorIndication-IEs}},
    ...
}

ErrorIndication-IEs X2AP-PROTOCOL-IES ::= {
    { ID id-Old-eNB-UE-X2AP-ID                  CRITICALITY ignore  TYPE UE-X2AP-ID                         PRESENCE optional}|
    { ID id-New-eNB-UE-X2AP-ID                  CRITICALITY ignore  TYPE UE-X2AP-ID                         PRESENCE optional}|
    { ID id-Cause                               CRITICALITY ignore  TYPE Cause                              PRESENCE optional}|
    { ID id-CriticalityDiagnostics              CRITICALITY ignore  TYPE CriticalityDiagnostics             PRESENCE optional}|
    { ID id-Old-eNB-UE-X2AP-ID-Extension        CRITICALITY ignore  TYPE UE-X2AP-ID-Extension               PRESENCE optional}|
    { ID id-New-eNB-UE-X2AP-ID-Extension        CRITICALITY ignore  TYPE UE-X2AP-ID-Extension               PRESENCE optional}|
    { ID id-Old-SgNB-UE-X2AP-ID                 CRITICALITY ignore  TYPE SgNB-UE-X2AP-ID                    PRESENCE optional}|
    { ID id-InterfaceInstanceIndication         CRITICALITY reject  TYPE InterfaceInstanceIndication        PRESENCE optional},
    ...
}

-- **************************************************************
--
-- RESET REQUEST
--
-- **************************************************************

ResetRequest ::= SEQUENCE {
    protocolIEs     ProtocolIE-Container    {{ResetRequest-IEs}},
    ...
}

ResetRequest-IEs X2AP-PROTOCOL-IES ::= {
    { ID id-Cause                           CRITICALITY ignore  TYPE Cause                          PRESENCE mandatory}|
    { ID id-InterfaceInstanceIndication     CRITICALITY reject  TYPE InterfaceInstanceIndication    PRESENCE optional},
    ...
}

-- **************************************************************
--
-- RESET RESPONSE
--
-- **************************************************************

ResetResponse ::= SEQUENCE {
    protocolIEs     ProtocolIE-Container    {{ResetResponse-IEs}},
    ...
}

ResetResponse-IEs X2AP-PROTOCOL-IES ::= {
    { ID id-CriticalityDiagnostics          CRITICALITY ignore  TYPE CriticalityDiagnostics         PRESENCE optional }|
    { ID id-InterfaceInstanceIndication     CRITICALITY reject  TYPE InterfaceInstanceIndication        PRESENCE optional},
    ...
}

-- **************************************************************
--
-- X2 SETUP REQUEST
--
-- **************************************************************

X2SetupRequest ::= SEQUENCE {
    protocolIEs     ProtocolIE-Container    {{X2SetupRequest-IEs}},
    ...
}

X2SetupRequest-IEs X2AP-PROTOCOL-IES ::= {
    { ID id-GlobalENB-ID            CRITICALITY reject  TYPE GlobalENB-ID           PRESENCE mandatory}|
    { ID id-ServedCells             CRITICALITY reject  TYPE ServedCells            PRESENCE mandatory}|
    { ID id-GUGroupIDList           CRITICALITY reject  TYPE GUGroupIDList          PRESENCE optional}|
    { ID id-LHN-ID                  CRITICALITY ignore  TYPE LHN-ID                 PRESENCE optional},
...
}



-- **************************************************************
--
-- X2 SETUP RESPONSE
--
-- **************************************************************

X2SetupResponse ::= SEQUENCE {
    protocolIEs     ProtocolIE-Container    {{X2SetupResponse-IEs}},
    ...
}

X2SetupResponse-IEs X2AP-PROTOCOL-IES ::= {
    { ID id-GlobalENB-ID                CRITICALITY reject  TYPE GlobalENB-ID           PRESENCE mandatory}|
    { ID id-ServedCells                 CRITICALITY reject  TYPE ServedCells            PRESENCE mandatory}|
    { ID id-GUGroupIDList               CRITICALITY reject  TYPE GUGroupIDList          PRESENCE optional}|
    { ID id-CriticalityDiagnostics      CRITICALITY ignore  TYPE CriticalityDiagnostics PRESENCE optional}|
    { ID id-LHN-ID                      CRITICALITY ignore  TYPE LHN-ID                 PRESENCE optional},
    ...
}



-- **************************************************************
--
-- X2 SETUP FAILURE
--
-- **************************************************************

X2SetupFailure ::= SEQUENCE {
    protocolIEs     ProtocolIE-Container    {{X2SetupFailure-IEs}},
    ...
}

X2SetupFailure-IEs X2AP-PROTOCOL-IES ::= {
    { ID id-Cause                   CRITICALITY ignore      TYPE Cause                              PRESENCE mandatory} |
    { ID id-TimeToWait              CRITICALITY ignore      TYPE TimeToWait                         PRESENCE optional} |
    { ID id-CriticalityDiagnostics  CRITICALITY ignore      TYPE CriticalityDiagnostics             PRESENCE optional },

    ...
}



-- **************************************************************
--
-- LOAD INFORMATION
--
-- **************************************************************

LoadInformation ::= SEQUENCE {
    protocolIEs     ProtocolIE-Container    {{LoadInformation-IEs}},
    ...
}

LoadInformation-IEs X2AP-PROTOCOL-IES ::= {
    { ID id-CellInformation             CRITICALITY ignore  TYPE CellInformation-List       PRESENCE mandatory} ,
    ...
}

CellInformation-List ::= SEQUENCE (SIZE (1..maxCellineNB)) OF ProtocolIE-Single-Container { {CellInformation-ItemIEs} }

CellInformation-ItemIEs X2AP-PROTOCOL-IES ::= {
    { ID id-CellInformation-Item    CRITICALITY ignore  TYPE CellInformation-Item   PRESENCE mandatory  }
}

CellInformation-Item ::= SEQUENCE {
    cell-ID                         ECGI,
    ul-InterferenceOverloadIndication       UL-InterferenceOverloadIndication       OPTIONAL,
    ul-HighInterferenceIndicationInfo       UL-HighInterferenceIndicationInfo       OPTIONAL,
    relativeNarrowbandTxPower               RelativeNarrowbandTxPower               OPTIONAL,
    iE-Extensions                           ProtocolExtensionContainer { {CellInformation-Item-ExtIEs} }    OPTIONAL,
    ...
}

CellInformation-Item-ExtIEs X2AP-PROTOCOL-EXTENSION ::= {
{ ID id-ABSInformation                      CRITICALITY ignore  EXTENSION ABSInformation                            PRESENCE optional }|
{ ID id-InvokeIndication                    CRITICALITY ignore  EXTENSION InvokeIndication                          PRESENCE optional }|
{ ID id-IntendedULDLConfiguration           CRITICALITY ignore  EXTENSION SubframeAssignment                        PRESENCE optional }|
{ ID id-ExtendedULInterferenceOverloadInfo  CRITICALITY ignore  EXTENSION ExtendedULInterferenceOverloadInfo    PRESENCE optional }|
{ ID id-CoMPInformation                     CRITICALITY ignore  EXTENSION CoMPInformation                           PRESENCE optional }|
{ ID id-DynamicDLTransmissionInformation    CRITICALITY ignore  EXTENSION DynamicDLTransmissionInformation      PRESENCE optional },
    ...
}

-- **************************************************************
--
-- ENB CONFIGURATION UPDATE
--
-- **************************************************************

ENBConfigurationUpdate ::= SEQUENCE {
    protocolIEs     ProtocolIE-Container    {{ENBConfigurationUpdate-IEs}},
    ...
}

ENBConfigurationUpdate-IEs X2AP-PROTOCOL-IES ::= {
    { ID id-ServedCellsToAdd            CRITICALITY reject  TYPE ServedCells                    PRESENCE optional}|
    { ID id-ServedCellsToModify         CRITICALITY reject  TYPE ServedCellsToModify            PRESENCE optional}|
    { ID id-ServedCellsToDelete         CRITICALITY reject  TYPE Old-ECGIs                      PRESENCE optional}|
    { ID id-GUGroupIDToAddList          CRITICALITY reject  TYPE GUGroupIDList                  PRESENCE optional}|
    { ID id-GUGroupIDToDeleteList       CRITICALITY reject  TYPE GUGroupIDList                  PRESENCE optional}|
    { ID id-CoverageModificationList    CRITICALITY reject  TYPE CoverageModificationList       PRESENCE optional},
    ...
}

ServedCellsToModify::= SEQUENCE (SIZE (1..maxCellineNB)) OF ServedCellsToModify-Item

ServedCellsToModify-Item::= SEQUENCE {
    old-ecgi                        ECGI,
    servedCellInfo                  ServedCell-Information,
    neighbour-Info                  Neighbour-Information           OPTIONAL,
    iE-Extensions                   ProtocolExtensionContainer { {ServedCellsToModify-Item-ExtIEs} } OPTIONAL,
    ...
}

ServedCellsToModify-Item-ExtIEs X2AP-PROTOCOL-EXTENSION ::= {
    { ID id-DeactivationIndication          CRITICALITY ignore  EXTENSION DeactivationIndication                PRESENCE optional }|
    { ID id-NRNeighbourInfoToModify         CRITICALITY ignore  EXTENSION NRNeighbour-Information               PRESENCE optional },
    ...
}


Old-ECGIs::= SEQUENCE (SIZE (1..maxCellineNB)) OF ECGI

-- **************************************************************
--
-- ENB CONFIGURATION UPDATE ACKNOWLEDGE
--
-- **************************************************************

ENBConfigurationUpdateAcknowledge ::= SEQUENCE {
    protocolIEs     ProtocolIE-Container    {{ENBConfigurationUpdateAcknowledge-IEs}},
    ...
}

ENBConfigurationUpdateAcknowledge-IEs X2AP-PROTOCOL-IES ::= {
    { ID id-CriticalityDiagnostics      CRITICALITY ignore  TYPE CriticalityDiagnostics         PRESENCE optional},
...
}

-- **************************************************************
--
-- ENB CONFIGURATION UPDATE FAIURE
--
-- **************************************************************

ENBConfigurationUpdateFailure ::= SEQUENCE {
    protocolIEs     ProtocolIE-Container    {{ENBConfigurationUpdateFailure-IEs}},
    ...
}

ENBConfigurationUpdateFailure-IEs X2AP-PROTOCOL-IES ::= {
    { ID id-Cause                       CRITICALITY ignore  TYPE Cause                      PRESENCE mandatory}|
    { ID id-TimeToWait                  CRITICALITY ignore  TYPE TimeToWait                 PRESENCE optional}|
    { ID id-CriticalityDiagnostics      CRITICALITY ignore  TYPE CriticalityDiagnostics     PRESENCE optional},
    ...
}



-- **************************************************************
--
-- RESOURCE STATUS REQUEST
--
-- **************************************************************

ResourceStatusRequest ::= SEQUENCE {
    protocolIEs     ProtocolIE-Container    {{ResourceStatusRequest-IEs}},
    ...
}

ResourceStatusRequest-IEs X2AP-PROTOCOL-IES ::= {
    { ID id-ENB1-Measurement-ID         CRITICALITY reject  TYPE Measurement-ID                 PRESENCE mandatory}|
    { ID id-ENB2-Measurement-ID         CRITICALITY ignore  TYPE Measurement-ID                 PRESENCE conditional}|-- The IE shall be present if the Registration Request IE is set to “Stop”, “Partial stop” or to “Add”--
    { ID id-Registration-Request        CRITICALITY reject  TYPE Registration-Request           PRESENCE mandatory}|
    { ID id-ReportCharacteristics       CRITICALITY reject  TYPE ReportCharacteristics          PRESENCE optional}|
    { ID id-CellToReport                CRITICALITY ignore  TYPE CellToReport-List              PRESENCE mandatory}|
    { ID id-ReportingPeriodicity        CRITICALITY ignore  TYPE ReportingPeriodicity           PRESENCE optional}|
    { ID id-PartialSuccessIndicator     CRITICALITY ignore  TYPE PartialSuccessIndicator        PRESENCE optional}|
    { ID id-ReportingPeriodicityRSRPMR  CRITICALITY ignore  TYPE ReportingPeriodicityRSRPMR     PRESENCE optional}|
    { ID id-ReportingPeriodicityCSIR    CRITICALITY ignore  TYPE ReportingPeriodicityCSIR       PRESENCE optional},
    ...
}


CellToReport-List       ::= SEQUENCE (SIZE (1..maxCellineNB)) OF ProtocolIE-Single-Container { {CellToReport-ItemIEs} }

CellToReport-ItemIEs X2AP-PROTOCOL-IES ::= {
    { ID id-CellToReport-Item   CRITICALITY ignore  TYPE CellToReport-Item  PRESENCE mandatory}
}

CellToReport-Item ::= SEQUENCE {
    cell-ID                                 ECGI,
    iE-Extensions                           ProtocolExtensionContainer { {CellToReport-Item-ExtIEs} } OPTIONAL,
    ...
}

CellToReport-Item-ExtIEs X2AP-PROTOCOL-EXTENSION ::= {
    ...
}


ReportingPeriodicity ::= ENUMERATED {
    one-thousand-ms,
    two-thousand-ms,
    five-thousand-ms,
    ten-thousand-ms,
...
}

PartialSuccessIndicator ::= ENUMERATED {
    partial-success-allowed,
...
}

-- **************************************************************
--
-- RESOURCE STATUS RESPONSE
--
-- **************************************************************

ResourceStatusResponse ::= SEQUENCE {
    protocolIEs     ProtocolIE-Container    {{ResourceStatusResponse-IEs}},
    ...
}

ResourceStatusResponse-IEs X2AP-PROTOCOL-IES ::= {
    { ID id-ENB1-Measurement-ID                 CRITICALITY reject  TYPE Measurement-ID                         PRESENCE mandatory}|
    { ID id-ENB2-Measurement-ID                 CRITICALITY reject  TYPE Measurement-ID                         PRESENCE mandatory}|
    { ID id-CriticalityDiagnostics              CRITICALITY ignore  TYPE CriticalityDiagnostics                 PRESENCE optional}|
    { ID id-MeasurementInitiationResult-List    CRITICALITY ignore  TYPE MeasurementInitiationResult-List   PRESENCE optional},
    ...
}


MeasurementInitiationResult-List ::= SEQUENCE (SIZE (1..maxCellineNB)) OF ProtocolIE-Single-Container { {MeasurementInitiationResult-ItemIEs} }

MeasurementInitiationResult-ItemIEs X2AP-PROTOCOL-IES ::= {
    { ID id-MeasurementInitiationResult-Item    CRITICALITY ignore  TYPE MeasurementInitiationResult-Item   PRESENCE mandatory}
}

MeasurementInitiationResult-Item ::= SEQUENCE {
    cell-ID                                         ECGI,
    measurementFailureCause-List                    MeasurementFailureCause-List    OPTIONAL,
    iE-Extensions                                   ProtocolExtensionContainer { {MeasurementInitiationResult-Item-ExtIEs} }    OPTIONAL,
    ...
}

MeasurementInitiationResult-Item-ExtIEs X2AP-PROTOCOL-EXTENSION ::= {
    ...
}

MeasurementFailureCause-List ::= SEQUENCE (SIZE (1..maxFailedMeasObjects)) OF ProtocolIE-Single-Container { {MeasurementFailureCause-ItemIEs} }

MeasurementFailureCause-ItemIEs X2AP-PROTOCOL-IES ::= {
    { ID id-MeasurementFailureCause-Item    CRITICALITY ignore  TYPE MeasurementFailureCause-Item       PRESENCE mandatory}
}

MeasurementFailureCause-Item ::= SEQUENCE {
    measurementFailedReportCharacteristics          ReportCharacteristics,
    cause                                           Cause,
    iE-Extensions                                   ProtocolExtensionContainer { {MeasurementFailureCause-Item-ExtIEs} }    OPTIONAL,
    ...
}

MeasurementFailureCause-Item-ExtIEs X2AP-PROTOCOL-EXTENSION ::= {
    ...
}

-- **************************************************************
--
-- RESOURCE STATUS FAILURE
--
-- **************************************************************

ResourceStatusFailure ::= SEQUENCE {
    protocolIEs     ProtocolIE-Container    {{ResourceStatusFailure-IEs}},
    ...
}

ResourceStatusFailure-IEs X2AP-PROTOCOL-IES ::= {
    { ID id-ENB1-Measurement-ID                     CRITICALITY reject  TYPE Measurement-ID                                 PRESENCE mandatory}|
    { ID id-ENB2-Measurement-ID                     CRITICALITY reject  TYPE Measurement-ID                                 PRESENCE mandatory}|
    { ID id-Cause                                   CRITICALITY ignore  TYPE Cause                                          PRESENCE mandatory}|
    { ID id-CriticalityDiagnostics                  CRITICALITY ignore  TYPE CriticalityDiagnostics                     PRESENCE optional}|
    { ID id-CompleteFailureCauseInformation-List    CRITICALITY ignore  TYPE CompleteFailureCauseInformation-List   PRESENCE optional},
    ...
}

CompleteFailureCauseInformation-List ::= SEQUENCE (SIZE (1..maxCellineNB)) OF ProtocolIE-Single-Container { {CompleteFailureCauseInformation-ItemIEs} }

CompleteFailureCauseInformation-ItemIEs X2AP-PROTOCOL-IES ::= {
    { ID id-CompleteFailureCauseInformation-Item    CRITICALITY ignore  TYPE CompleteFailureCauseInformation-Item   PRESENCE mandatory}
}

CompleteFailureCauseInformation-Item ::= SEQUENCE {
    cell-ID                                         ECGI,
    measurementFailureCause-List                    MeasurementFailureCause-List,
    iE-Extensions                                   ProtocolExtensionContainer { {CompleteFailureCauseInformation-Item-ExtIEs} }    OPTIONAL,
    ...
}

CompleteFailureCauseInformation-Item-ExtIEs X2AP-PROTOCOL-EXTENSION ::= {
    ...
}

-- **************************************************************
--
-- RESOURCE STATUS UPDATE
--
-- **************************************************************

ResourceStatusUpdate ::= SEQUENCE {
    protocolIEs     ProtocolIE-Container    {{ResourceStatusUpdate-IEs}},
    ...
}

ResourceStatusUpdate-IEs X2AP-PROTOCOL-IES ::= {
    { ID id-ENB1-Measurement-ID     CRITICALITY reject  TYPE Measurement-ID                 PRESENCE mandatory}|
    { ID id-ENB2-Measurement-ID     CRITICALITY reject  TYPE Measurement-ID                 PRESENCE mandatory}|
    { ID id-CellMeasurementResult   CRITICALITY ignore  TYPE CellMeasurementResult-List     PRESENCE mandatory},
    ...
}

CellMeasurementResult-List ::= SEQUENCE (SIZE (1..maxCellineNB)) OF ProtocolIE-Single-Container { {CellMeasurementResult-ItemIEs} }

CellMeasurementResult-ItemIEs X2AP-PROTOCOL-IES ::= {
    { ID id-CellMeasurementResult-Item  CRITICALITY ignore  TYPE CellMeasurementResult-Item PRESENCE mandatory}
}

CellMeasurementResult-Item ::= SEQUENCE {
    cell-ID                     ECGI,
    hWLoadIndicator             HWLoadIndicator     OPTIONAL,
    s1TNLLoadIndicator          S1TNLLoadIndicator  OPTIONAL,
    radioResourceStatus         RadioResourceStatus OPTIONAL,
    iE-Extensions               ProtocolExtensionContainer { {CellMeasurementResult-Item-ExtIEs} }  OPTIONAL,
    ...
}

CellMeasurementResult-Item-ExtIEs X2AP-PROTOCOL-EXTENSION ::= {
    { ID id-CompositeAvailableCapacityGroup CRITICALITY ignore  EXTENSION CompositeAvailableCapacityGroup       PRESENCE optional}|
    { ID id-ABS-Status                      CRITICALITY ignore  EXTENSION ABS-Status                                PRESENCE optional}|
    { ID id-RSRPMRList                      CRITICALITY ignore  EXTENSION RSRPMRList                                PRESENCE optional}|
    { ID id-CSIReportList                   CRITICALITY ignore  EXTENSION CSIReportList                             PRESENCE optional}|
    { ID id-CellReportingIndicator          CRITICALITY ignore  EXTENSION CellReportingIndicator                    PRESENCE optional}|
    { ID id-MeasurementResultforNRCellsPossiblyAggregated       CRITICALITY ignore  EXTENSION MeasurementResultforNRCellsPossiblyAggregated             PRESENCE optional},
    ...
}


-- **************************************************************
--
-- PRIVATE MESSAGE
--
-- **************************************************************

PrivateMessage ::= SEQUENCE {
    privateIEs      PrivateIE-Container {{PrivateMessage-IEs}},
    ...
}

PrivateMessage-IEs X2AP-PRIVATE-IES ::= {
    ...
}

-- **************************************************************
--
-- MOBILITY CHANGE REQUEST
--
-- **************************************************************

MobilityChangeRequest ::= SEQUENCE {
    protocolIEs     ProtocolIE-Container    {{MobilityChangeRequest-IEs}},
    ...
}

MobilityChangeRequest-IEs X2AP-PROTOCOL-IES ::= {
    { ID id-ENB1-Cell-ID                        CRITICALITY reject  TYPE ECGI                                           PRESENCE mandatory}|
    { ID id-ENB2-Cell-ID                        CRITICALITY reject  TYPE ECGI                                           PRESENCE mandatory}|
    { ID id-ENB1-Mobility-Parameters            CRITICALITY ignore  TYPE MobilityParametersInformation              PRESENCE optional}|
    { ID id-ENB2-Proposed-Mobility-Parameters   CRITICALITY reject  TYPE MobilityParametersInformation              PRESENCE mandatory}|
    { ID id-Cause                               CRITICALITY reject  TYPE Cause                                          PRESENCE mandatory},
    ...
}

-- **************************************************************
--
-- MOBILITY CHANGE ACKNOWLEDGE
--
-- **************************************************************

MobilityChangeAcknowledge ::= SEQUENCE {
    protocolIEs     ProtocolIE-Container    {{MobilityChangeAcknowledge-IEs}},
    ...
}

MobilityChangeAcknowledge-IEs X2AP-PROTOCOL-IES ::= {
    { ID id-ENB1-Cell-ID            CRITICALITY reject  TYPE ECGI                           PRESENCE mandatory}|
    { ID id-ENB2-Cell-ID            CRITICALITY reject  TYPE ECGI                           PRESENCE mandatory}|
    { ID id-CriticalityDiagnostics  CRITICALITY ignore  TYPE CriticalityDiagnostics         PRESENCE optional},
    ...
}


-- **************************************************************
--
-- MOBILITY CHANGE FAILURE
--
-- **************************************************************

MobilityChangeFailure ::= SEQUENCE {
    protocolIEs     ProtocolIE-Container    {{MobilityChangeFailure-IEs}},
    ...
}

MobilityChangeFailure-IEs X2AP-PROTOCOL-IES ::= {
    { ID id-ENB1-Cell-ID                                    CRITICALITY ignore  TYPE ECGI                                               PRESENCE mandatory}|
    { ID id-ENB2-Cell-ID                                    CRITICALITY ignore  TYPE ECGI                                               PRESENCE mandatory}|
    { ID id-Cause                                           CRITICALITY ignore  TYPE Cause                                              PRESENCE mandatory}|
    { ID id-ENB2-Mobility-Parameters-Modification-Range     CRITICALITY ignore  TYPE MobilityParametersModificationRange        PRESENCE optional}|
    { ID id-CriticalityDiagnostics                          CRITICALITY ignore  TYPE CriticalityDiagnostics                     PRESENCE optional},
    ...
}

-- **************************************************************
--
-- RADIO LINK FAILURE INDICATION
--
-- **************************************************************

RLFIndication ::= SEQUENCE {
    protocolIEs     ProtocolIE-Container    {{RLFIndication-IEs}},
    ...
}

RLFIndication-IEs X2AP-PROTOCOL-IES ::= {
    { ID id-FailureCellPCI                              CRITICALITY ignore  TYPE PCI                                                        PRESENCE mandatory}|
    { ID id-Re-establishmentCellECGI                    CRITICALITY ignore  TYPE ECGI                                                       PRESENCE mandatory}|
    { ID id-FailureCellCRNTI                            CRITICALITY ignore  TYPE CRNTI                                                      PRESENCE mandatory}|
    { ID id-ShortMAC-I                                  CRITICALITY ignore  TYPE ShortMAC-I                                                 PRESENCE optional}|
    { ID id-UE-RLF-Report-Container                     CRITICALITY ignore  TYPE UE-RLF-Report-Container                                PRESENCE optional}|
    { ID id-RRCConnSetupIndicator                       CRITICALITY reject  TYPE RRCConnSetupIndicator                                  PRESENCE optional}|
    { ID id-RRCConnReestabIndicator                     CRITICALITY ignore  TYPE RRCConnReestabIndicator                                PRESENCE optional}|
    { ID id-UE-RLF-Report-Container-for-extended-bands  CRITICALITY ignore  TYPE UE-RLF-Report-Container-for-extended-bands     PRESENCE optional}|
    { ID id-NBIoT-RLF-Report-Container                  CRITICALITY ignore  TYPE NBIoT-RLF-Report-Container                         PRESENCE optional},
    ...
}


-- **************************************************************
--
-- CELL ACTIVATION REQUEST
--
-- **************************************************************

CellActivationRequest ::= SEQUENCE {
    protocolIEs     ProtocolIE-Container    {{CellActivationRequest-IEs}},
    ...
}

CellActivationRequest-IEs X2AP-PROTOCOL-IES ::= {
    { ID id-ServedCellsToActivate   CRITICALITY reject  TYPE ServedCellsToActivate      PRESENCE mandatory},
    ...
}

ServedCellsToActivate::= SEQUENCE (SIZE (1..maxCellineNB)) OF ServedCellsToActivate-Item

ServedCellsToActivate-Item::= SEQUENCE {
    ecgi                        ECGI,
    iE-Extensions                   ProtocolExtensionContainer { {ServedCellsToActivate-Item-ExtIEs} } OPTIONAL,
    ...
}

ServedCellsToActivate-Item-ExtIEs X2AP-PROTOCOL-EXTENSION ::= {
    ...
}

-- **************************************************************
--
-- CELL ACTIVATION RESPONSE
--
-- **************************************************************

CellActivationResponse ::= SEQUENCE {
    protocolIEs     ProtocolIE-Container    {{CellActivationResponse-IEs}},
    ...
}

CellActivationResponse-IEs X2AP-PROTOCOL-IES ::= {
    { ID id-ActivatedCellList       CRITICALITY ignore  TYPE ActivatedCellList              PRESENCE mandatory}|
    { ID id-CriticalityDiagnostics  CRITICALITY ignore  TYPE CriticalityDiagnostics         PRESENCE optional},
    ...
}

ActivatedCellList ::= SEQUENCE (SIZE (1..maxCellineNB)) OF ActivatedCellList-Item

ActivatedCellList-Item::= SEQUENCE {
    ecgi                                ECGI,
    iE-Extensions                       ProtocolExtensionContainer { {ActivatedCellList-Item-ExtIEs} } OPTIONAL,
    ...
}

ActivatedCellList-Item-ExtIEs X2AP-PROTOCOL-EXTENSION ::= {
    ...
}

--**************************************************************
--
-- CELL ACTIVATION FAILURE
--
-- **************************************************************

CellActivationFailure ::= SEQUENCE {
    protocolIEs     ProtocolIE-Container    {{CellActivationFailure-IEs}},
    ...
}

CellActivationFailure-IEs X2AP-PROTOCOL-IES ::= {
    { ID id-Cause                       CRITICALITY ignore  TYPE Cause                      PRESENCE mandatory }|
    { ID id-CriticalityDiagnostics      CRITICALITY ignore  TYPE CriticalityDiagnostics     PRESENCE optional },
    ...
}

-- **************************************************************
--
-- X2 RELEASE
--
-- **************************************************************

X2Release ::= SEQUENCE {
    protocolIEs     ProtocolIE-Container    {{X2Release-IEs}},
    ...
}

X2Release-IEs X2AP-PROTOCOL-IES ::= {
    { ID id-GlobalENB-ID            CRITICALITY reject  TYPE GlobalENB-ID           PRESENCE mandatory},
...
}

-- **************************************************************
--
-- X2AP MESSAGE TRANSFER
--
-- **************************************************************

X2APMessageTransfer ::= SEQUENCE {
    protocolIEs     ProtocolIE-Container    {{X2APMessageTransfer-IEs}},
    ...
}

X2APMessageTransfer-IEs X2AP-PROTOCOL-IES ::= {
    { ID id-RNL-Header  CRITICALITY reject  TYPE RNL-Header             PRESENCE mandatory}|
    { ID id-x2APMessage CRITICALITY reject  TYPE X2AP-Message           PRESENCE optional},
    ...
}

RNL-Header ::= SEQUENCE {
    source-GlobalENB-ID GlobalENB-ID,
    target-GlobalENB-ID GlobalENB-ID    OPTIONAL,
    iE-Extensions                       ProtocolExtensionContainer { {RNL-Header-Item-ExtIEs} } OPTIONAL,
    ...
}

RNL-Header-Item-ExtIEs X2AP-PROTOCOL-EXTENSION ::= {
    ...
}

X2AP-Message ::= OCTET STRING

-- **************************************************************
--
-- SENB ADDITION REQUEST
--
-- **************************************************************

SeNBAdditionRequest ::= SEQUENCE {
    protocolIEs     ProtocolIE-Container    {{SeNBAdditionRequest-IEs}},
    ...
}

SeNBAdditionRequest-IEs X2AP-PROTOCOL-IES ::= {
    { ID id-MeNB-UE-X2AP-ID                 CRITICALITY reject  TYPE UE-X2AP-ID                         PRESENCE mandatory}|
    { ID id-UE-SecurityCapabilities         CRITICALITY reject  TYPE UESecurityCapabilities             PRESENCE conditional}|
    -- This IE shall be present if the Bearer Option IE is set to the value “SCG bearer” --
    { ID id-SeNBSecurityKey                 CRITICALITY reject  TYPE SeNBSecurityKey                    PRESENCE conditional}|
    -- This IE shall be present if the Bearer Option IE is set to the value “SCG bearer” --
    { ID id-SeNBUEAggregateMaximumBitRate   CRITICALITY reject  TYPE UEAggregateMaximumBitRate          PRESENCE mandatory}|
    { ID id-ServingPLMN                     CRITICALITY ignore  TYPE PLMN-Identity                      PRESENCE optional}|
    { ID id-E-RABs-ToBeAdded-List           CRITICALITY reject  TYPE E-RABs-ToBeAdded-List              PRESENCE mandatory}|
    { ID id-MeNBtoSeNBContainer             CRITICALITY reject  TYPE MeNBtoSeNBContainer                PRESENCE mandatory}|
    { ID id-CSGMembershipStatus             CRITICALITY reject  TYPE CSGMembershipStatus                PRESENCE optional}|
    { ID id-SeNB-UE-X2AP-ID                 CRITICALITY reject  TYPE UE-X2AP-ID                         PRESENCE optional}|
    { ID id-SeNB-UE-X2AP-ID-Extension       CRITICALITY reject  TYPE UE-X2AP-ID-Extension               PRESENCE optional}|
    { ID id-ExpectedUEBehaviour             CRITICALITY ignore  TYPE ExpectedUEBehaviour                PRESENCE optional}|
    { ID id-MeNB-UE-X2AP-ID-Extension       CRITICALITY reject  TYPE UE-X2AP-ID-Extension               PRESENCE optional},
    ...
}

E-RABs-ToBeAdded-List ::= SEQUENCE (SIZE(1..maxnoofBearers)) OF ProtocolIE-Single-Container { {E-RABs-ToBeAdded-ItemIEs} }

E-RABs-ToBeAdded-ItemIEs X2AP-PROTOCOL-IES ::= {
    { ID id-E-RABs-ToBeAdded-Item   CRITICALITY reject  TYPE E-RABs-ToBeAdded-Item      PRESENCE mandatory},
    ...
}

E-RABs-ToBeAdded-Item ::= CHOICE {
    sCG-Bearer      E-RABs-ToBeAdded-Item-SCG-Bearer,
    split-Bearer    E-RABs-ToBeAdded-Item-Split-Bearer,
    ...
}

E-RABs-ToBeAdded-Item-SCG-Bearer ::= SEQUENCE {
    e-RAB-ID                        E-RAB-ID,
    e-RAB-Level-QoS-Parameters      E-RAB-Level-QoS-Parameters,
    dL-Forwarding                   DL-Forwarding                                                                   OPTIONAL,
    s1-UL-GTPtunnelEndpoint         GTPtunnelEndpoint,
    iE-Extensions                   ProtocolExtensionContainer { {E-RABs-ToBeAdded-Item-SCG-BearerExtIEs} } OPTIONAL,
    ...
}

E-RABs-ToBeAdded-Item-SCG-BearerExtIEs X2AP-PROTOCOL-EXTENSION ::= {
    { ID id-Correlation-ID              CRITICALITY ignore  EXTENSION Correlation-ID        PRESENCE optional}|
    { ID id-SIPTO-Correlation-ID        CRITICALITY ignore  EXTENSION Correlation-ID        PRESENCE optional}|
    { ID id-BearerType                  CRITICALITY ignore  EXTENSION BearerType            PRESENCE optional}|
    { ID id-Ethernet-Type               CRITICALITY ignore  EXTENSION Ethernet-Type         PRESENCE optional}|
    { ID id-SourceDLForwardingIPAddress         CRITICALITY ignore  EXTENSION TransportLayerAddress     PRESENCE optional},
    ...
}

E-RABs-ToBeAdded-Item-Split-Bearer ::= SEQUENCE {
    e-RAB-ID                        E-RAB-ID,
    e-RAB-Level-QoS-Parameters      E-RAB-Level-QoS-Parameters,
    meNB-GTPtunnelEndpoint          GTPtunnelEndpoint,
    iE-Extensions                   ProtocolExtensionContainer { {E-RABs-ToBeAdded-Item-Split-BearerExtIEs} } OPTIONAL,
    ...
}

E-RABs-ToBeAdded-Item-Split-BearerExtIEs X2AP-PROTOCOL-EXTENSION ::= {
    { ID id-SourceDLForwardingIPAddress         CRITICALITY ignore  EXTENSION TransportLayerAddress     PRESENCE optional},
    ...
}

-- **************************************************************
--
-- SENB ADDITION REQUEST ACKNOWLEDGE
--
-- **************************************************************

SeNBAdditionRequestAcknowledge ::= SEQUENCE {
    protocolIEs     ProtocolIE-Container    {{SeNBAdditionRequestAcknowledge-IEs}},
    ...
}

SeNBAdditionRequestAcknowledge-IEs X2AP-PROTOCOL-IES ::= {
    { ID id-MeNB-UE-X2AP-ID                     CRITICALITY reject  TYPE UE-X2AP-ID                         PRESENCE mandatory}|
    { ID id-SeNB-UE-X2AP-ID                     CRITICALITY reject  TYPE UE-X2AP-ID                         PRESENCE mandatory}|
    { ID id-E-RABs-Admitted-ToBeAdded-List      CRITICALITY ignore  TYPE E-RABs-Admitted-ToBeAdded-List PRESENCE mandatory}|
    { ID id-E-RABs-NotAdmitted-List             CRITICALITY ignore  TYPE E-RAB-List                         PRESENCE optional}|
    { ID id-SeNBtoMeNBContainer                 CRITICALITY reject  TYPE SeNBtoMeNBContainer                PRESENCE mandatory}|
    { ID id-CriticalityDiagnostics              CRITICALITY ignore  TYPE CriticalityDiagnostics             PRESENCE optional}|
    { ID id-GW-TransportLayerAddress            CRITICALITY ignore  TYPE TransportLayerAddress              PRESENCE optional}|
    { ID id-SIPTO-L-GW-TransportLayerAddress    CRITICALITY ignore  TYPE TransportLayerAddress              PRESENCE optional}|
    { ID id-MeNB-UE-X2AP-ID-Extension           CRITICALITY reject  TYPE UE-X2AP-ID-Extension               PRESENCE optional}|
    { ID id-SeNB-UE-X2AP-ID-Extension           CRITICALITY reject  TYPE UE-X2AP-ID-Extension               PRESENCE optional}|
    { ID id-Tunnel-Information-for-BBF          CRITICALITY ignore  TYPE TunnelInformation                  PRESENCE optional},
    ...
}

E-RABs-Admitted-ToBeAdded-List ::= SEQUENCE (SIZE (1..maxnoofBearers)) OF ProtocolIE-Single-Container { {E-RABs-Admitted-ToBeAdded-ItemIEs} }

E-RABs-Admitted-ToBeAdded-ItemIEs X2AP-PROTOCOL-IES ::= {
    { ID id-E-RABs-Admitted-ToBeAdded-Item  CRITICALITY ignore  TYPE E-RABs-Admitted-ToBeAdded-Item         PRESENCE mandatory}
}

E-RABs-Admitted-ToBeAdded-Item ::= CHOICE {
    sCG-Bearer      E-RABs-Admitted-ToBeAdded-Item-SCG-Bearer,
    split-Bearer    E-RABs-Admitted-ToBeAdded-Item-Split-Bearer,
    ...
}

E-RABs-Admitted-ToBeAdded-Item-SCG-Bearer ::= SEQUENCE {
    e-RAB-ID                                E-RAB-ID,
    s1-DL-GTPtunnelEndpoint                 GTPtunnelEndpoint,
    dL-Forwarding-GTPtunnelEndpoint         GTPtunnelEndpoint                                                                   OPTIONAL,
    uL-Forwarding-GTPtunnelEndpoint         GTPtunnelEndpoint                                                                   OPTIONAL,
    iE-Extensions                   ProtocolExtensionContainer { {E-RABs-Admitted-ToBeAdded-Item-SCG-BearerExtIEs} }    OPTIONAL,
    ...
}

E-RABs-Admitted-ToBeAdded-Item-SCG-BearerExtIEs X2AP-PROTOCOL-EXTENSION ::= {
    { ID id-SourceDLForwardingIPAddress             CRITICALITY ignore  EXTENSION TransportLayerAddress     PRESENCE optional},
    ...
}

E-RABs-Admitted-ToBeAdded-Item-Split-Bearer ::= SEQUENCE {
    e-RAB-ID                        E-RAB-ID,
    seNB-GTPtunnelEndpoint          GTPtunnelEndpoint,
    iE-Extensions                   ProtocolExtensionContainer { {E-RABs-Admitted-ToBeAdded-Item-Split-BearerExtIEs} } OPTIONAL,
    ...
}

E-RABs-Admitted-ToBeAdded-Item-Split-BearerExtIEs X2AP-PROTOCOL-EXTENSION ::= {
    { ID id-SourceDLForwardingIPAddress         CRITICALITY ignore  EXTENSION TransportLayerAddress     PRESENCE optional},
    ...
}

-- **************************************************************
--
-- SENB ADDITION REQUEST REJECT
--
-- **************************************************************

SeNBAdditionRequestReject ::= SEQUENCE {
    protocolIEs     ProtocolIE-Container    {{SeNBAdditionRequestReject-IEs}},
    ...
}

SeNBAdditionRequestReject-IEs X2AP-PROTOCOL-IES ::= {
    { ID id-MeNB-UE-X2AP-ID                 CRITICALITY reject  TYPE UE-X2AP-ID                 PRESENCE mandatory}|
    { ID id-SeNB-UE-X2AP-ID                 CRITICALITY reject  TYPE UE-X2AP-ID                 PRESENCE mandatory}|
    { ID id-Cause                           CRITICALITY ignore  TYPE Cause                      PRESENCE mandatory}|
    { ID id-CriticalityDiagnostics          CRITICALITY ignore  TYPE CriticalityDiagnostics     PRESENCE optional}|
    { ID id-MeNB-UE-X2AP-ID-Extension       CRITICALITY reject  TYPE UE-X2AP-ID-Extension       PRESENCE optional}|
    { ID id-SeNB-UE-X2AP-ID-Extension       CRITICALITY reject  TYPE UE-X2AP-ID-Extension       PRESENCE optional},
    ...
}

-- **************************************************************
--
-- SENB RECONFIGURATION COMPLETE
--
-- **************************************************************

SeNBReconfigurationComplete ::= SEQUENCE {
    protocolIEs     ProtocolIE-Container    {{SeNBReconfigurationComplete-IEs}},
    ...
}

SeNBReconfigurationComplete-IEs X2AP-PROTOCOL-IES ::= {
    { ID id-MeNB-UE-X2AP-ID                         CRITICALITY reject  TYPE UE-X2AP-ID                                 PRESENCE mandatory}|
    { ID id-SeNB-UE-X2AP-ID                         CRITICALITY reject  TYPE UE-X2AP-ID                                 PRESENCE mandatory}|
    { ID id-ResponseInformationSeNBReconfComp       CRITICALITY ignore  TYPE ResponseInformationSeNBReconfComp  PRESENCE mandatory}|
    { ID id-MeNB-UE-X2AP-ID-Extension               CRITICALITY reject  TYPE UE-X2AP-ID-Extension                       PRESENCE optional}|
    { ID id-SeNB-UE-X2AP-ID-Extension               CRITICALITY reject  TYPE UE-X2AP-ID-Extension                       PRESENCE optional},
    ...
}

ResponseInformationSeNBReconfComp ::= CHOICE {
    success             ResponseInformationSeNBReconfComp-SuccessItem,
    reject-by-MeNB      ResponseInformationSeNBReconfComp-RejectByMeNBItem,
    ...
}

ResponseInformationSeNBReconfComp-SuccessItem ::= SEQUENCE {
    meNBtoSeNBContainer             MeNBtoSeNBContainer OPTIONAL,
    iE-Extensions                   ProtocolExtensionContainer { {ResponseInformationSeNBReconfComp-SuccessItemExtIEs} }    OPTIONAL,
    ...
}

ResponseInformationSeNBReconfComp-SuccessItemExtIEs X2AP-PROTOCOL-EXTENSION ::= {
    ...
}

ResponseInformationSeNBReconfComp-RejectByMeNBItem ::= SEQUENCE {
    cause                           Cause,
    meNBtoSeNBContainer             MeNBtoSeNBContainer                                                                                     OPTIONAL,
    iE-Extensions                   ProtocolExtensionContainer { {ResponseInformationSeNBReconfComp-RejectByMeNBItemExtIEs} }   OPTIONAL,
    ...
}

ResponseInformationSeNBReconfComp-RejectByMeNBItemExtIEs X2AP-PROTOCOL-EXTENSION ::= {
    ...
}

-- **************************************************************
--
-- SENB MODIFICATION REQUEST
--
-- **************************************************************

SeNBModificationRequest ::= SEQUENCE {
    protocolIEs     ProtocolIE-Container    {{ SeNBModificationRequest-IEs}},
    ...
}

SeNBModificationRequest-IEs X2AP-PROTOCOL-IES ::= {
    { ID id-MeNB-UE-X2AP-ID                     CRITICALITY reject  TYPE UE-X2AP-ID                             PRESENCE mandatory}|
    { ID id-SeNB-UE-X2AP-ID                     CRITICALITY reject  TYPE UE-X2AP-ID                             PRESENCE mandatory}|
    { ID id-Cause                               CRITICALITY ignore  TYPE Cause                                  PRESENCE mandatory}|
    { ID id-SCGChangeIndication                 CRITICALITY ignore  TYPE SCGChangeIndication                    PRESENCE optional}|
    { ID id-ServingPLMN                         CRITICALITY ignore  TYPE PLMN-Identity                          PRESENCE optional}|
    { ID id-UE-ContextInformationSeNBModReq     CRITICALITY reject  TYPE UE-ContextInformationSeNBModReq    PRESENCE optional}|
    { ID id-MeNBtoSeNBContainer                 CRITICALITY ignore  TYPE MeNBtoSeNBContainer                    PRESENCE optional}|
    { ID id-CSGMembershipStatus                 CRITICALITY reject  TYPE CSGMembershipStatus                    PRESENCE optional}|
    { ID id-MeNB-UE-X2AP-ID-Extension           CRITICALITY reject  TYPE UE-X2AP-ID-Extension                   PRESENCE optional}|
    { ID id-SeNB-UE-X2AP-ID-Extension           CRITICALITY reject  TYPE UE-X2AP-ID-Extension                   PRESENCE optional},
    ...
}

UE-ContextInformationSeNBModReq ::= SEQUENCE {
    uE-SecurityCapabilities         UESecurityCapabilities                                                          OPTIONAL,
    seNB-SecurityKey                SeNBSecurityKey                                                                 OPTIONAL,
    seNBUEAggregateMaximumBitRate   UEAggregateMaximumBitRate                                                       OPTIONAL,
    e-RABs-ToBeAdded                E-RABs-ToBeAdded-List-ModReq                                                    OPTIONAL,
    e-RABs-ToBeModified             E-RABs-ToBeModified-List-ModReq                                                 OPTIONAL,
    e-RABs-ToBeReleased             E-RABs-ToBeReleased-List-ModReq                                                 OPTIONAL,
    iE-Extensions                   ProtocolExtensionContainer { {UE-ContextInformationSeNBModReqExtIEs} }      OPTIONAL,
    ...
}

UE-ContextInformationSeNBModReqExtIEs X2AP-PROTOCOL-EXTENSION ::= {
    ...
}

E-RABs-ToBeAdded-List-ModReq ::= SEQUENCE (SIZE(1..maxnoofBearers)) OF ProtocolIE-Single-Container { {E-RABs-ToBeAdded-ModReqItemIEs} }

E-RABs-ToBeAdded-ModReqItemIEs X2AP-PROTOCOL-IES ::= {
    { ID id-E-RABs-ToBeAdded-ModReqItem CRITICALITY ignore  TYPE E-RABs-ToBeAdded-ModReqItem    PRESENCE mandatory},
    ...
}

E-RABs-ToBeAdded-ModReqItem ::= CHOICE {
    sCG-Bearer      E-RABs-ToBeAdded-ModReqItem-SCG-Bearer,
    split-Bearer    E-RABs-ToBeAdded-ModReqItem-Split-Bearer,
    ...
}

E-RABs-ToBeAdded-ModReqItem-SCG-Bearer ::= SEQUENCE {
    e-RAB-ID                        E-RAB-ID,
    e-RAB-Level-QoS-Parameters      E-RAB-Level-QoS-Parameters,
    dL-Forwarding                   DL-Forwarding                                                                   OPTIONAL,
    s1-UL-GTPtunnelEndpoint         GTPtunnelEndpoint,
    iE-Extensions                   ProtocolExtensionContainer { {E-RABs-ToBeAdded-ModReqItem-SCG-BearerExtIEs} } OPTIONAL,
    ...
}

E-RABs-ToBeAdded-ModReqItem-SCG-BearerExtIEs X2AP-PROTOCOL-EXTENSION ::= {
    { ID id-Correlation-ID              CRITICALITY ignore  EXTENSION Correlation-ID        PRESENCE optional}|
    { ID id-SIPTO-Correlation-ID        CRITICALITY ignore  EXTENSION Correlation-ID        PRESENCE optional}|
    { ID id-BearerType                  CRITICALITY ignore  EXTENSION BearerType            PRESENCE optional}|
    { ID id-Ethernet-Type               CRITICALITY ignore  EXTENSION Ethernet-Type         PRESENCE optional}|
    { ID id-SourceDLForwardingIPAddress CRITICALITY ignore  EXTENSION TransportLayerAddress PRESENCE optional},
    ...
}

E-RABs-ToBeAdded-ModReqItem-Split-Bearer ::= SEQUENCE {
    e-RAB-ID                        E-RAB-ID,
    e-RAB-Level-QoS-Parameters      E-RAB-Level-QoS-Parameters,
    meNB-GTPtunnelEndpoint          GTPtunnelEndpoint,
    iE-Extensions                   ProtocolExtensionContainer { {E-RABs-ToBeAdded-ModReqItem-Split-BearerExtIEs} } OPTIONAL,
    ...
}

E-RABs-ToBeAdded-ModReqItem-Split-BearerExtIEs X2AP-PROTOCOL-EXTENSION ::= {
{ ID id-SourceDLForwardingIPAddress         CRITICALITY ignore  EXTENSION TransportLayerAddress     PRESENCE optional},
    ...
}

E-RABs-ToBeModified-List-ModReq ::= SEQUENCE (SIZE(1..maxnoofBearers)) OF ProtocolIE-Single-Container { {E-RABs-ToBeModified-ModReqItemIEs} }

E-RABs-ToBeModified-ModReqItemIEs X2AP-PROTOCOL-IES ::= {
    { ID id-E-RABs-ToBeModified-ModReqItem  CRITICALITY ignore  TYPE E-RABs-ToBeModified-ModReqItem     PRESENCE mandatory},
    ...
}


E-RABs-ToBeModified-ModReqItem ::= CHOICE {
    sCG-Bearer      E-RABs-ToBeModified-ModReqItem-SCG-Bearer,
    split-Bearer    E-RABs-ToBeModified-ModReqItem-Split-Bearer,
    ...
}

E-RABs-ToBeModified-ModReqItem-SCG-Bearer ::= SEQUENCE {
    e-RAB-ID                        E-RAB-ID,
    e-RAB-Level-QoS-Parameters      E-RAB-Level-QoS-Parameters                                                      OPTIONAL,
    s1-UL-GTPtunnelEndpoint         GTPtunnelEndpoint                                                               OPTIONAL,
    iE-Extensions                   ProtocolExtensionContainer { {E-RABs-ToBeModified-ModReqItem-SCG-BearerExtIEs} } OPTIONAL,
    ...
}

E-RABs-ToBeModified-ModReqItem-SCG-BearerExtIEs X2AP-PROTOCOL-EXTENSION ::= {
    ...
}

E-RABs-ToBeModified-ModReqItem-Split-Bearer ::= SEQUENCE {
    e-RAB-ID                        E-RAB-ID,
    e-RAB-Level-QoS-Parameters      E-RAB-Level-QoS-Parameters                                                              OPTIONAL,
    meNB-GTPtunnelEndpoint          GTPtunnelEndpoint                                                                       OPTIONAL,
    iE-Extensions                   ProtocolExtensionContainer { {E-RABs-ToBeModified-ModReqItem-Split-BearerExtIEs} } OPTIONAL,
    ...
}

E-RABs-ToBeModified-ModReqItem-Split-BearerExtIEs X2AP-PROTOCOL-EXTENSION ::= {
    ...
}

E-RABs-ToBeReleased-List-ModReq ::= SEQUENCE (SIZE(1..maxnoofBearers)) OF ProtocolIE-Single-Container { {E-RABs-ToBeReleased-ModReqItemIEs} }

E-RABs-ToBeReleased-ModReqItemIEs X2AP-PROTOCOL-IES ::= {
    { ID id-E-RABs-ToBeReleased-ModReqItem  CRITICALITY ignore  TYPE E-RABs-ToBeReleased-ModReqItem     PRESENCE mandatory},
    ...
}

E-RABs-ToBeReleased-ModReqItem ::= CHOICE {
    sCG-Bearer      E-RABs-ToBeReleased-ModReqItem-SCG-Bearer,
    split-Bearer    E-RABs-ToBeReleased-ModReqItem-Split-Bearer,
    ...
}

E-RABs-ToBeReleased-ModReqItem-SCG-Bearer ::= SEQUENCE {
    e-RAB-ID                        E-RAB-ID,
    dL-Forwarding-GTPtunnelEndpoint         GTPtunnelEndpoint                                               OPTIONAL,
    uL-Forwarding-GTPtunnelEndpoint         GTPtunnelEndpoint                                               OPTIONAL,
    iE-Extensions                   ProtocolExtensionContainer { {E-RABs-ToBeReleased-ModReqItem-SCG-BearerExtIEs} } OPTIONAL,
    ...
}

E-RABs-ToBeReleased-ModReqItem-SCG-BearerExtIEs X2AP-PROTOCOL-EXTENSION ::= {
    ...
}

E-RABs-ToBeReleased-ModReqItem-Split-Bearer ::= SEQUENCE {
    e-RAB-ID                        E-RAB-ID,
    dL-Forwarding-GTPtunnelEndpoint         GTPtunnelEndpoint                                               OPTIONAL,
    iE-Extensions                   ProtocolExtensionContainer { {E-RABs-ToBeReleased-ModReqItem-Split-BearerExtIEs} } OPTIONAL,
    ...
}

E-RABs-ToBeReleased-ModReqItem-Split-BearerExtIEs X2AP-PROTOCOL-EXTENSION ::= {
    ...
}

-- **************************************************************
--
-- SENB MODIFICATION REQUEST ACKNOWLEDGE
--
-- **************************************************************

SeNBModificationRequestAcknowledge ::= SEQUENCE {
    protocolIEs     ProtocolIE-Container    {{SeNBModificationRequestAcknowledge-IEs}},
    ...
}

SeNBModificationRequestAcknowledge-IEs X2AP-PROTOCOL-IES ::= {
    { ID id-MeNB-UE-X2AP-ID                             CRITICALITY ignore  TYPE UE-X2AP-ID                                         PRESENCE mandatory}|
    { ID id-SeNB-UE-X2AP-ID                             CRITICALITY ignore  TYPE UE-X2AP-ID                                         PRESENCE mandatory}|
    { ID id-E-RABs-Admitted-ToBeAdded-ModAckList        CRITICALITY ignore  TYPE E-RABs-Admitted-ToBeAdded-ModAckList       PRESENCE optional}|
    { ID id-E-RABs-Admitted-ToBeModified-ModAckList     CRITICALITY ignore  TYPE E-RABs-Admitted-ToBeModified-ModAckList    PRESENCE optional}|
    { ID id-E-RABs-Admitted-ToBeReleased-ModAckList     CRITICALITY ignore  TYPE E-RABs-Admitted-ToBeReleased-ModAckList    PRESENCE optional}|
    { ID id-E-RABs-NotAdmitted-List                     CRITICALITY ignore  TYPE E-RAB-List                                         PRESENCE optional}|
    { ID id-SeNBtoMeNBContainer                         CRITICALITY ignore  TYPE SeNBtoMeNBContainer                                PRESENCE optional}|
    { ID id-CriticalityDiagnostics                      CRITICALITY ignore  TYPE CriticalityDiagnostics                         PRESENCE optional}|
    { ID id-MeNB-UE-X2AP-ID-Extension                   CRITICALITY ignore  TYPE UE-X2AP-ID-Extension                           PRESENCE optional}|
    { ID id-SeNB-UE-X2AP-ID-Extension                   CRITICALITY ignore  TYPE UE-X2AP-ID-Extension                           PRESENCE optional},
    ...
}

E-RABs-Admitted-ToBeAdded-ModAckList ::= SEQUENCE (SIZE (1..maxnoofBearers)) OF ProtocolIE-Single-Container { {E-RABs-Admitted-ToBeAdded-ModAckItemIEs} }

E-RABs-Admitted-ToBeAdded-ModAckItemIEs X2AP-PROTOCOL-IES ::= {
    { ID id-E-RABs-Admitted-ToBeAdded-ModAckItem    CRITICALITY ignore  TYPE E-RABs-Admitted-ToBeAdded-ModAckItem       PRESENCE mandatory}
}

E-RABs-Admitted-ToBeAdded-ModAckItem ::= CHOICE {
    sCG-Bearer      E-RABs-Admitted-ToBeAdded-ModAckItem-SCG-Bearer,
    split-Bearer    E-RABs-Admitted-ToBeAdded-ModAckItem-Split-Bearer,
    ...
}

E-RABs-Admitted-ToBeAdded-ModAckItem-SCG-Bearer ::= SEQUENCE {
    e-RAB-ID                                E-RAB-ID,
    s1-DL-GTPtunnelEndpoint                 GTPtunnelEndpoint,
    dL-Forwarding-GTPtunnelEndpoint         GTPtunnelEndpoint                                                                   OPTIONAL,
    uL-Forwarding-GTPtunnelEndpoint         GTPtunnelEndpoint                                                                   OPTIONAL,
    iE-Extensions                           ProtocolExtensionContainer { {E-RABs-Admitted-ToBeAdded-ModAckItem-SCG-BearerExtIEs} }  OPTIONAL,
    ...
}

E-RABs-Admitted-ToBeAdded-ModAckItem-SCG-BearerExtIEs X2AP-PROTOCOL-EXTENSION ::= {
{ ID id-SourceDLForwardingIPAddress     CRITICALITY ignore  EXTENSION TransportLayerAddress     PRESENCE optional},
    ...
}

E-RABs-Admitted-ToBeAdded-ModAckItem-Split-Bearer ::= SEQUENCE {
    e-RAB-ID                        E-RAB-ID,
    seNB-GTPtunnelEndpoint          GTPtunnelEndpoint,
    iE-Extensions                   ProtocolExtensionContainer { {E-RABs-Admitted-ToBeAdded-ModAckItem-Split-BearerExtIEs} } OPTIONAL,
    ...
}

E-RABs-Admitted-ToBeAdded-ModAckItem-Split-BearerExtIEs X2AP-PROTOCOL-EXTENSION ::= {
{ ID id-SourceDLForwardingIPAddress     CRITICALITY ignore  EXTENSION TransportLayerAddress     PRESENCE optional},
    ...
}
E-RABs-Admitted-ToBeModified-ModAckList ::= SEQUENCE (SIZE (1..maxnoofBearers)) OF ProtocolIE-Single-Container { {E-RABs-Admitted-ToBeModified-ModAckItemIEs} }

E-RABs-Admitted-ToBeModified-ModAckItemIEs X2AP-PROTOCOL-IES ::= {
    { ID id-E-RABs-Admitted-ToBeModified-ModAckItem     CRITICALITY ignore  TYPE E-RABs-Admitted-ToBeModified-ModAckItem    PRESENCE mandatory}
}

E-RABs-Admitted-ToBeModified-ModAckItem ::= CHOICE {
    sCG-Bearer      E-RABs-Admitted-ToBeModified-ModAckItem-SCG-Bearer,
    split-Bearer    E-RABs-Admitted-ToBeModified-ModAckItem-Split-Bearer,
    ...
}

E-RABs-Admitted-ToBeModified-ModAckItem-SCG-Bearer ::= SEQUENCE {
    e-RAB-ID                        E-RAB-ID,
    s1-DL-GTPtunnelEndpoint         GTPtunnelEndpoint                                                                   OPTIONAL,
    iE-Extensions                   ProtocolExtensionContainer { {E-RABs-Admitted-ToBeModified-ModAckItem-SCG-BearerExtIEs} } OPTIONAL,
    ...
}

E-RABs-Admitted-ToBeModified-ModAckItem-SCG-BearerExtIEs X2AP-PROTOCOL-EXTENSION ::= {
    ...
}

E-RABs-Admitted-ToBeModified-ModAckItem-Split-Bearer ::= SEQUENCE {
    e-RAB-ID                        E-RAB-ID,
    seNB-GTPtunnelEndpoint          GTPtunnelEndpoint                                                                           OPTIONAL,
    iE-Extensions                   ProtocolExtensionContainer { {E-RABs-Admitted-ToBeModified-ModAckItem-Split-BearerExtIEs} } OPTIONAL,
    ...
}

E-RABs-Admitted-ToBeModified-ModAckItem-Split-BearerExtIEs X2AP-PROTOCOL-EXTENSION ::= {
    ...
}

E-RABs-Admitted-ToBeReleased-ModAckList ::= SEQUENCE (SIZE (1..maxnoofBearers)) OF ProtocolIE-Single-Container { {E-RABs-Admitted-ToBeReleased-ModAckItemIEs} }

E-RABs-Admitted-ToBeReleased-ModAckItemIEs X2AP-PROTOCOL-IES ::= {
    { ID id-E-RABs-Admitted-ToBeReleased-ModAckItem     CRITICALITY ignore  TYPE E-RABs-Admitted-ToReleased-ModAckItem      PRESENCE mandatory}
}

E-RABs-Admitted-ToReleased-ModAckItem ::= CHOICE {
    sCG-Bearer      E-RABs-Admitted-ToBeReleased-ModAckItem-SCG-Bearer,
    split-Bearer    E-RABs-Admitted-ToBeReleased-ModAckItem-Split-Bearer,
    ...
}

E-RABs-Admitted-ToBeReleased-ModAckItem-SCG-Bearer ::= SEQUENCE {
    e-RAB-ID                    E-RAB-ID,
    iE-Extensions               ProtocolExtensionContainer { {E-RABs-Admitted-ToBeReleased-ModAckItem-SCG-BearerExtIEs} }   OPTIONAL,
    ...
}

E-RABs-Admitted-ToBeReleased-ModAckItem-SCG-BearerExtIEs X2AP-PROTOCOL-EXTENSION ::= {
    ...
}

E-RABs-Admitted-ToBeReleased-ModAckItem-Split-Bearer ::= SEQUENCE {
    e-RAB-ID                    E-RAB-ID,
    iE-Extensions               ProtocolExtensionContainer { {E-RABs-Admitted-ToBeReleased-ModAckItem-Split-BearerExtIEs} } OPTIONAL,
    ...
}

E-RABs-Admitted-ToBeReleased-ModAckItem-Split-BearerExtIEs X2AP-PROTOCOL-EXTENSION ::= {
    ...
}

-- **************************************************************
--
-- SENB MODIFICATION REQUEST REJECT
--
-- **************************************************************

SeNBModificationRequestReject ::= SEQUENCE {
    protocolIEs     ProtocolIE-Container    {{SeNBModificationRequestReject-IEs}},
    ...
}

SeNBModificationRequestReject-IEs X2AP-PROTOCOL-IES ::= {
    { ID id-MeNB-UE-X2AP-ID                     CRITICALITY ignore  TYPE UE-X2AP-ID                 PRESENCE mandatory}|
    { ID id-SeNB-UE-X2AP-ID                     CRITICALITY ignore  TYPE UE-X2AP-ID                 PRESENCE mandatory}|
    { ID id-Cause                               CRITICALITY ignore  TYPE Cause                      PRESENCE mandatory}|
    { ID id-CriticalityDiagnostics              CRITICALITY ignore  TYPE CriticalityDiagnostics     PRESENCE optional}|
    { ID id-MeNB-UE-X2AP-ID-Extension           CRITICALITY ignore  TYPE UE-X2AP-ID-Extension       PRESENCE optional}|
    { ID id-SeNB-UE-X2AP-ID-Extension           CRITICALITY ignore  TYPE UE-X2AP-ID-Extension       PRESENCE optional},
    ...
}

-- **************************************************************
--
-- SENB MODIFICATION REQUIRED
--
-- **************************************************************

SeNBModificationRequired ::= SEQUENCE {
    protocolIEs     ProtocolIE-Container        {{SeNBModificationRequired-IEs}},
    ...
}

SeNBModificationRequired-IEs X2AP-PROTOCOL-IES ::= {
    { ID id-MeNB-UE-X2AP-ID                     CRITICALITY reject  TYPE UE-X2AP-ID                         PRESENCE mandatory}|
    { ID id-SeNB-UE-X2AP-ID                     CRITICALITY reject  TYPE UE-X2AP-ID                         PRESENCE mandatory}|
    { ID id-Cause                               CRITICALITY ignore  TYPE Cause                              PRESENCE mandatory}|
    { ID id-SCGChangeIndication                 CRITICALITY ignore  TYPE SCGChangeIndication                PRESENCE optional}|
    { ID id-E-RABs-ToBeReleased-ModReqd         CRITICALITY ignore  TYPE E-RABs-ToBeReleased-ModReqd        PRESENCE optional}|
    { ID id-SeNBtoMeNBContainer                 CRITICALITY ignore  TYPE SeNBtoMeNBContainer                PRESENCE optional}|
    { ID id-MeNB-UE-X2AP-ID-Extension           CRITICALITY reject  TYPE UE-X2AP-ID-Extension               PRESENCE optional}|
    { ID id-SeNB-UE-X2AP-ID-Extension           CRITICALITY reject  TYPE UE-X2AP-ID-Extension               PRESENCE optional},
    ...
}


E-RABs-ToBeReleased-ModReqd ::= SEQUENCE (SIZE (1..maxnoofBearers)) OF ProtocolIE-Single-Container { {E-RABs-ToBeReleased-ModReqdItemIEs} }

E-RABs-ToBeReleased-ModReqdItemIEs X2AP-PROTOCOL-IES ::= {
    { ID id-E-RABs-ToBeReleased-ModReqdItem  CRITICALITY ignore     TYPE E-RABs-ToBeReleased-ModReqdItem    PRESENCE mandatory },
    ...
}

E-RABs-ToBeReleased-ModReqdItem ::= SEQUENCE {
    e-RAB-ID                        E-RAB-ID,
    cause                           Cause,
    iE-Extensions                   ProtocolExtensionContainer { {E-RABs-ToBeReleased-ModReqdItemExtIEs} } OPTIONAL,
    ...
}

E-RABs-ToBeReleased-ModReqdItemExtIEs X2AP-PROTOCOL-EXTENSION ::= {
    ...
}

-- **************************************************************
--
-- SENB MODIFICATION CONFIRM
--
-- **************************************************************

SeNBModificationConfirm ::= SEQUENCE {
    protocolIEs     ProtocolIE-Container    {{SeNBModificationConfirm-IEs}},
    ...
}

SeNBModificationConfirm-IEs X2AP-PROTOCOL-IES ::= {
    { ID id-MeNB-UE-X2AP-ID                     CRITICALITY ignore  TYPE UE-X2AP-ID                     PRESENCE mandatory}|
    { ID id-SeNB-UE-X2AP-ID                     CRITICALITY ignore  TYPE UE-X2AP-ID                     PRESENCE mandatory}|
    { ID id-MeNBtoSeNBContainer                 CRITICALITY ignore  TYPE MeNBtoSeNBContainer            PRESENCE optional}|
    { ID id-CriticalityDiagnostics              CRITICALITY ignore  TYPE CriticalityDiagnostics         PRESENCE optional}|
    { ID id-MeNB-UE-X2AP-ID-Extension           CRITICALITY ignore  TYPE UE-X2AP-ID-Extension           PRESENCE optional}|
    { ID id-SeNB-UE-X2AP-ID-Extension           CRITICALITY ignore  TYPE UE-X2AP-ID-Extension           PRESENCE optional},
    ...
}

-- **************************************************************
--
-- SENB MODIFICATION REFUSE
--
-- **************************************************************

SeNBModificationRefuse ::= SEQUENCE {
    protocolIEs     ProtocolIE-Container        {{SeNBModificationRefuse-IEs}},
    ...
}

SeNBModificationRefuse-IEs X2AP-PROTOCOL-IES ::= {
    { ID id-MeNB-UE-X2AP-ID                     CRITICALITY ignore  TYPE UE-X2AP-ID                 PRESENCE mandatory}|
    { ID id-SeNB-UE-X2AP-ID                     CRITICALITY ignore  TYPE UE-X2AP-ID                 PRESENCE mandatory}|
    { ID id-Cause                               CRITICALITY ignore  TYPE Cause                      PRESENCE mandatory}|
    { ID id-MeNBtoSeNBContainer                 CRITICALITY ignore  TYPE MeNBtoSeNBContainer        PRESENCE optional}|
    { ID id-CriticalityDiagnostics              CRITICALITY ignore  TYPE CriticalityDiagnostics     PRESENCE optional}|
    { ID id-MeNB-UE-X2AP-ID-Extension           CRITICALITY ignore  TYPE UE-X2AP-ID-Extension       PRESENCE optional}|
    { ID id-SeNB-UE-X2AP-ID-Extension           CRITICALITY ignore  TYPE UE-X2AP-ID-Extension       PRESENCE optional},
    ...
}

-- **************************************************************
--
-- SENB RELEASE REQUEST
--
-- **************************************************************

SeNBReleaseRequest ::= SEQUENCE {
    protocolIEs     ProtocolIE-Container        {{SeNBReleaseRequest-IEs}},
    ...
}

SeNBReleaseRequest-IEs X2AP-PROTOCOL-IES ::= {
    { ID id-MeNB-UE-X2AP-ID                     CRITICALITY reject  TYPE UE-X2AP-ID                                 PRESENCE mandatory}|
    { ID id-SeNB-UE-X2AP-ID                     CRITICALITY reject  TYPE UE-X2AP-ID                                 PRESENCE optional}|
    { ID id-Cause                               CRITICALITY ignore  TYPE Cause                                      PRESENCE optional}|
    { ID id-E-RABs-ToBeReleased-List-RelReq     CRITICALITY ignore  TYPE E-RABs-ToBeReleased-List-RelReq        PRESENCE optional}|
    { ID id-UE-ContextKeptIndicator             CRITICALITY ignore  TYPE UE-ContextKeptIndicator                    PRESENCE optional}|
    { ID id-MeNB-UE-X2AP-ID-Extension           CRITICALITY reject  TYPE UE-X2AP-ID-Extension                       PRESENCE optional}|
    { ID id-SeNB-UE-X2AP-ID-Extension           CRITICALITY reject  TYPE UE-X2AP-ID-Extension                       PRESENCE optional}|
    { ID id-MakeBeforeBreakIndicator            CRITICALITY ignore  TYPE MakeBeforeBreakIndicator                   PRESENCE optional},
    ...
}
E-RABs-ToBeReleased-List-RelReq ::= SEQUENCE (SIZE(1..maxnoofBearers)) OF ProtocolIE-Single-Container { {E-RABs-ToBeReleased-RelReqItemIEs} }

E-RABs-ToBeReleased-RelReqItemIEs X2AP-PROTOCOL-IES ::= {
    { ID id-E-RABs-ToBeReleased-RelReqItem      CRITICALITY ignore  TYPE E-RABs-ToBeReleased-RelReqItem     PRESENCE mandatory},
    ...
}

E-RABs-ToBeReleased-RelReqItem ::= CHOICE {
    sCG-Bearer      E-RABs-ToBeReleased-RelReqItem-SCG-Bearer,
    split-Bearer    E-RABs-ToBeReleased-RelReqItem-Split-Bearer,
    ...
}

E-RABs-ToBeReleased-RelReqItem-SCG-Bearer ::= SEQUENCE {
    e-RAB-ID                        E-RAB-ID,
    uL-Forwarding-GTPtunnelEndpoint         GTPtunnelEndpoint                                               OPTIONAL,
    dL-Forwarding-GTPtunnelEndpoint         GTPtunnelEndpoint                                               OPTIONAL,
    iE-Extensions                   ProtocolExtensionContainer { {E-RABs-ToBeReleased-RelReqItem-SCG-BearerExtIEs} } OPTIONAL,
    ...
}

E-RABs-ToBeReleased-RelReqItem-SCG-BearerExtIEs X2AP-PROTOCOL-EXTENSION ::= {
    ...
}

E-RABs-ToBeReleased-RelReqItem-Split-Bearer ::= SEQUENCE {
    e-RAB-ID                        E-RAB-ID,
    dL-Forwarding-GTPtunnelEndpoint         GTPtunnelEndpoint                                                   OPTIONAL,
    iE-Extensions                   ProtocolExtensionContainer { {E-RABs-ToBeReleased-RelReqItem-Split-BearerExtIEs} } OPTIONAL,
    ...
}

E-RABs-ToBeReleased-RelReqItem-Split-BearerExtIEs X2AP-PROTOCOL-EXTENSION ::= {
    ...
}

-- **************************************************************
--
-- SENB RELEASE REQUIRED
--
-- **************************************************************

SeNBReleaseRequired ::= SEQUENCE {
    protocolIEs     ProtocolIE-Container    {{SeNBReleaseRequired-IEs}},
    ...
}

SeNBReleaseRequired-IEs X2AP-PROTOCOL-IES ::= {
    { ID id-MeNB-UE-X2AP-ID                 CRITICALITY reject  TYPE UE-X2AP-ID                 PRESENCE mandatory}|
    { ID id-SeNB-UE-X2AP-ID                 CRITICALITY reject  TYPE UE-X2AP-ID                 PRESENCE mandatory}|
    { ID id-Cause                           CRITICALITY ignore  TYPE Cause                      PRESENCE mandatory}|
    { ID id-MeNB-UE-X2AP-ID-Extension       CRITICALITY reject  TYPE UE-X2AP-ID-Extension       PRESENCE optional}|
    { ID id-SeNB-UE-X2AP-ID-Extension       CRITICALITY reject  TYPE UE-X2AP-ID-Extension       PRESENCE optional},
    ...
}

-- **************************************************************
--
-- SENB RELEASE CONFIRM
--
-- **************************************************************

SeNBReleaseConfirm ::= SEQUENCE {
    protocolIEs     ProtocolIE-Container    {{SeNBReleaseConfirm-IEs}},
    ...
}

SeNBReleaseConfirm-IEs X2AP-PROTOCOL-IES ::= {
    { ID id-MeNB-UE-X2AP-ID                         CRITICALITY ignore  TYPE UE-X2AP-ID                                 PRESENCE mandatory}|
    { ID id-SeNB-UE-X2AP-ID                         CRITICALITY ignore  TYPE UE-X2AP-ID                                 PRESENCE mandatory}|
    { ID id-E-RABs-ToBeReleased-List-RelConf        CRITICALITY ignore  TYPE E-RABs-ToBeReleased-List-RelConf       PRESENCE optional}|
    { ID id-CriticalityDiagnostics                  CRITICALITY ignore  TYPE CriticalityDiagnostics                 PRESENCE optional}|
    { ID id-MeNB-UE-X2AP-ID-Extension               CRITICALITY ignore  TYPE UE-X2AP-ID-Extension                       PRESENCE optional}|
    { ID id-SeNB-UE-X2AP-ID-Extension               CRITICALITY ignore  TYPE UE-X2AP-ID-Extension                       PRESENCE optional},
    ...
}
E-RABs-ToBeReleased-List-RelConf ::= SEQUENCE (SIZE(1..maxnoofBearers)) OF ProtocolIE-Single-Container { {E-RABs-ToBeReleased-RelConfItemIEs} }

E-RABs-ToBeReleased-RelConfItemIEs X2AP-PROTOCOL-IES ::= {
    { ID id-E-RABs-ToBeReleased-RelConfItem     CRITICALITY ignore      TYPE E-RABs-ToBeReleased-RelConfItem        PRESENCE mandatory},
    ...
}

E-RABs-ToBeReleased-RelConfItem ::= CHOICE {
    sCG-Bearer      E-RABs-ToBeReleased-RelConfItem-SCG-Bearer,
    split-Bearer    E-RABs-ToBeReleased-RelConfItem-Split-Bearer,
    ...
}

E-RABs-ToBeReleased-RelConfItem-SCG-Bearer ::= SEQUENCE {
    e-RAB-ID                        E-RAB-ID,
    uL-Forwarding-GTPtunnelEndpoint         GTPtunnelEndpoint                                               OPTIONAL,
    dL-Forwarding-GTPtunnelEndpoint         GTPtunnelEndpoint                                               OPTIONAL,
    iE-Extensions                   ProtocolExtensionContainer { {E-RABs-ToBeReleased-RelConfItem-SCG-BearerExtIEs} } OPTIONAL,
    ...
}

E-RABs-ToBeReleased-RelConfItem-SCG-BearerExtIEs X2AP-PROTOCOL-EXTENSION ::= {
    ...
}

E-RABs-ToBeReleased-RelConfItem-Split-Bearer ::= SEQUENCE {
    e-RAB-ID                        E-RAB-ID,
    dL-Forwarding-GTPtunnelEndpoint         GTPtunnelEndpoint                                                   OPTIONAL,
    iE-Extensions                   ProtocolExtensionContainer { {E-RABs-ToBeReleased-RelConfItem-Split-BearerExtIEs} } OPTIONAL,
    ...
}

E-RABs-ToBeReleased-RelConfItem-Split-BearerExtIEs X2AP-PROTOCOL-EXTENSION ::= {
    ...
}

-- **************************************************************
--
-- SENB COUNTER CHECK REQUEST
--
-- **************************************************************

SeNBCounterCheckRequest ::= SEQUENCE {
    protocolIEs     ProtocolIE-Container    {{SeNBCounterCheckRequest-IEs}},
    ...
}

SeNBCounterCheckRequest-IEs X2AP-PROTOCOL-IES ::= {
    { ID id-MeNB-UE-X2AP-ID                     CRITICALITY reject  TYPE UE-X2AP-ID                                 PRESENCE mandatory}|
    { ID id-SeNB-UE-X2AP-ID                     CRITICALITY reject  TYPE UE-X2AP-ID                                 PRESENCE mandatory}|
    { ID id-E-RABs-SubjectToCounterCheck-List   CRITICALITY ignore  TYPE E-RABs-SubjectToCounterCheck-List      PRESENCE mandatory}|
    { ID id-MeNB-UE-X2AP-ID-Extension           CRITICALITY ignore  TYPE UE-X2AP-ID-Extension                       PRESENCE optional}|
    { ID id-SeNB-UE-X2AP-ID-Extension           CRITICALITY ignore  TYPE UE-X2AP-ID-Extension                       PRESENCE optional},
    ...
}
E-RABs-SubjectToCounterCheck-List ::= SEQUENCE (SIZE(1..maxnoofBearers)) OF ProtocolIE-Single-Container { {E-RABs-SubjectToCounterCheckItemIEs} }

E-RABs-SubjectToCounterCheckItemIEs X2AP-PROTOCOL-IES ::= {
    { ID id-E-RABs-SubjectToCounterCheckItem    CRITICALITY ignore  TYPE E-RABs-SubjectToCounterCheckItem       PRESENCE mandatory},
    ...
}

E-RABs-SubjectToCounterCheckItem ::= SEQUENCE {
    e-RAB-ID                        E-RAB-ID,
    uL-Count                        INTEGER (0..4294967295),
    dL-Count                        INTEGER (0..4294967295),
    iE-Extensions                   ProtocolExtensionContainer { {E-RABs-SubjectToCounterCheckItemExtIEs} } OPTIONAL,
    ...
}

E-RABs-SubjectToCounterCheckItemExtIEs X2AP-PROTOCOL-EXTENSION ::= {
    ...
}

-- **************************************************************
--
-- X2 REMOVAL REQUEST
--
-- **************************************************************

X2RemovalRequest ::= SEQUENCE {
    protocolIEs     ProtocolIE-Container    {{X2RemovalRequest-IEs}},
    ...
}

X2RemovalRequest-IEs X2AP-PROTOCOL-IES ::= {
    { ID id-GlobalENB-ID                CRITICALITY reject  TYPE GlobalENB-ID           PRESENCE mandatory}|
    { ID id-X2RemovalThreshold          CRITICALITY reject  TYPE X2BenefitValue         PRESENCE optional},
...
}



-- **************************************************************
--
-- X2 REMOVAL RESPONSE
--
-- **************************************************************

X2RemovalResponse ::= SEQUENCE {
    protocolIEs     ProtocolIE-Container    {{X2RemovalResponse-IEs}},
    ...
}

X2RemovalResponse-IEs X2AP-PROTOCOL-IES ::= {
    { ID id-GlobalENB-ID                CRITICALITY reject  TYPE GlobalENB-ID               PRESENCE mandatory}|
    { ID id-CriticalityDiagnostics      CRITICALITY ignore  TYPE CriticalityDiagnostics     PRESENCE optional},
    ...
}



-- **************************************************************
--
-- X2 REMOVAL FAILURE
--
-- **************************************************************

X2RemovalFailure ::= SEQUENCE {
    protocolIEs     ProtocolIE-Container    {{X2RemovalFailure-IEs}},
    ...
}

X2RemovalFailure-IEs X2AP-PROTOCOL-IES ::= {
    { ID id-Cause                       CRITICALITY ignore  TYPE Cause                          PRESENCE mandatory}|
    { ID id-CriticalityDiagnostics      CRITICALITY ignore  TYPE CriticalityDiagnostics         PRESENCE optional},
    ...
}


-- **************************************************************
--
-- RETRIEVE UE CONTEXT REQUEST
--
-- **************************************************************

RetrieveUEContextRequest ::= SEQUENCE {
    protocolIEs     ProtocolIE-Container    {{ RetrieveUEContextRequest-IEs}},
    ...
}

RetrieveUEContextRequest-IEs X2AP-PROTOCOL-IES ::= {
    { ID id-New-eNB-UE-X2AP-ID                  CRITICALITY reject  TYPE UE-X2AP-ID             PRESENCE mandatory}|
    { ID id-SeNB-UE-X2AP-ID-Extension           CRITICALITY reject  TYPE UE-X2AP-ID-Extension   PRESENCE optional}|
-- Allocated at the new eNB. --
-- This IE contains an Extended eNB UE X2AP ID, which, together with the New eNB UE X2AP ID IE --
-- represents the eNB UE X2AP ID allocated at the new eNB. --
    { ID id-resumeID                            CRITICALITY reject  TYPE ResumeID               PRESENCE mandatory}|
    { ID id-ShortMAC-I                          CRITICALITY reject  TYPE ShortMAC-I             PRESENCE mandatory}|
    { ID id-NewEUTRANCellIdentifier             CRITICALITY reject  TYPE EUTRANCellIdentifier   PRESENCE mandatory}|
    {ID id-FailureCellCRNTI                     CRITICALITY reject  TYPE CRNTI                  PRESENCE optional}|
    {ID id-FailureCellPCI                       CRITICALITY reject  TYPE PCI                    PRESENCE optional},
    ...
}

-- **************************************************************
--
-- RETRIEVE UE CONTEXT RESPONSE
--
-- **************************************************************

RetrieveUEContextResponse ::= SEQUENCE {
    protocolIEs         ProtocolIE-Container    {{ RetrieveUEContextResponse-IEs}},
    ...
}

RetrieveUEContextResponse-IEs X2AP-PROTOCOL-IES ::= {
    { ID id-New-eNB-UE-X2AP-ID                          CRITICALITY ignore  TYPE UE-X2AP-ID                                             PRESENCE mandatory}|
    { ID id-New-eNB-UE-X2AP-ID-Extension                CRITICALITY ignore  TYPE UE-X2AP-ID-Extension                               PRESENCE optional}|
    { ID id-Old-eNB-UE-X2AP-ID                          CRITICALITY ignore  TYPE UE-X2AP-ID                                             PRESENCE mandatory}|
    { ID id-Old-eNB-UE-X2AP-ID-Extension                CRITICALITY ignore  TYPE UE-X2AP-ID-Extension                               PRESENCE optional}|
    { ID id-GUMMEI-ID                                   CRITICALITY reject  TYPE GUMMEI                                                 PRESENCE mandatory}|
    { ID id-UE-ContextInformationRetrieve               CRITICALITY reject  TYPE UE-ContextInformationRetrieve                  PRESENCE mandatory}|
    { ID id-TraceActivation                             CRITICALITY ignore  TYPE TraceActivation                                        PRESENCE optional}|
    { ID id-SRVCCOperationPossible                      CRITICALITY ignore  TYPE SRVCCOperationPossible                             PRESENCE optional}|
    { ID id-Masked-IMEISV                               CRITICALITY ignore  TYPE Masked-IMEISV                                          PRESENCE optional}|
    { ID id-ExpectedUEBehaviour                         CRITICALITY ignore  TYPE ExpectedUEBehaviour                                    PRESENCE optional}|
    { ID id-ProSeAuthorized                             CRITICALITY ignore  TYPE ProSeAuthorized                                        PRESENCE optional}|
    { ID id-CriticalityDiagnostics                      CRITICALITY ignore  TYPE CriticalityDiagnostics                             PRESENCE optional}|
    { ID id-V2XServicesAuthorized                       CRITICALITY ignore  TYPE V2XServicesAuthorized                              PRESENCE optional}|
    { ID id-AerialUEsubscriptionInformation             CRITICALITY ignore  TYPE AerialUEsubscriptionInformation                    PRESENCE optional}|
    { ID id-Subscription-Based-UE-DifferentiationInfo   CRITICALITY ignore  TYPE Subscription-Based-UE-DifferentiationInfo  PRESENCE optional}|
    { ID id-NRV2XServicesAuthorized                     CRITICALITY ignore  TYPE NRV2XServicesAuthorized                            PRESENCE optional}|
    { ID id-PC5QoSParameters                            CRITICALITY ignore  TYPE PC5QoSParameters                                       PRESENCE optional },
    ...
}

UE-ContextInformationRetrieve ::= SEQUENCE {
    mME-UE-S1AP-ID                      UE-S1AP-ID,
    uESecurityCapabilities              UESecurityCapabilities,
    aS-SecurityInformation              AS-SecurityInformation,
    uEaggregateMaximumBitRate           UEAggregateMaximumBitRate,
    subscriberProfileIDforRFP           SubscriberProfileIDforRFP       OPTIONAL,
    e-RABs-ToBeSetup-ListRetrieve       E-RABs-ToBeSetup-ListRetrieve,
    rRC-Context                         RRC-Context,
    handoverRestrictionList             HandoverRestrictionList         OPTIONAL,
    locationReportingInformation        LocationReportingInformation    OPTIONAL,
    managBasedMDTallowed                ManagementBasedMDTallowed       OPTIONAL,
    managBasedMDTPLMNList               MDTPLMNList                     OPTIONAL,
    iE-Extensions                       ProtocolExtensionContainer { {UE-ContextInformationRetrieve-ExtIEs} } OPTIONAL,
    ...
}

UE-ContextInformationRetrieve-ExtIEs X2AP-PROTOCOL-EXTENSION ::= {
{ ID id-UESidelinkAggregateMaximumBitRate   CRITICALITY ignore  EXTENSION UESidelinkAggregateMaximumBitRate     PRESENCE optional }|
{ ID id-AdditionalRRMPriorityIndex          CRITICALITY ignore  EXTENSION AdditionalRRMPriorityIndex                    PRESENCE optional }|
{ ID id-EPCHandoverRestrictionListContainer CRITICALITY ignore  EXTENSION EPCHandoverRestrictionListContainer       PRESENCE optional }|
{ ID id-NRUESidelinkAggregateMaximumBitRate CRITICALITY ignore  EXTENSION NRUESidelinkAggregateMaximumBitRate       PRESENCE optional}|
{ ID id-UERadioCapabilityID                 CRITICALITY reject  EXTENSION UERadioCapabilityID                           PRESENCE optional }|
{ ID id-IMSvoiceEPSfallbackfrom5G           CRITICALITY ignore  EXTENSION IMSvoiceEPSfallbackfrom5G                 PRESENCE optional },
    ...
}

E-RABs-ToBeSetup-ListRetrieve ::= SEQUENCE (SIZE(1..maxnoofBearers)) OF ProtocolIE-Single-Container { {E-RABs-ToBeSetupRetrieve-ItemIEs} }

E-RABs-ToBeSetupRetrieve-ItemIEs    X2AP-PROTOCOL-IES ::= {
    { ID id-E-RABs-ToBeSetupRetrieve-Item   CRITICALITY ignore  TYPE E-RABs-ToBeSetupRetrieve-Item  PRESENCE mandatory},
    ...
}

E-RABs-ToBeSetupRetrieve-Item ::= SEQUENCE {
    e-RAB-ID                        E-RAB-ID,
    e-RAB-Level-QoS-Parameters      E-RAB-Level-QoS-Parameters,
    bearerType                      BearerType  OPTIONAL,
    iE-Extensions                   ProtocolExtensionContainer { {E-RABs-ToBeSetupRetrieve-ItemExtIEs} } OPTIONAL,
    ...
}

E-RABs-ToBeSetupRetrieve-ItemExtIEs X2AP-PROTOCOL-EXTENSION ::= {
    { ID id-uL-GTPtunnelEndpoint        CRITICALITY reject  EXTENSION GTPtunnelEndpoint     PRESENCE mandatory}|
    { ID id-dL-Forwarding               CRITICALITY ignore  EXTENSION DL-Forwarding         PRESENCE optional}|
    { ID id-Ethernet-Type               CRITICALITY ignore  EXTENSION Ethernet-Type         PRESENCE optional}|
    { ID id-SecurityIndication          CRITICALITY reject  EXTENSION SecurityIndication                PRESENCE optional}|
    { ID id-SourceDLForwardingIPAddress     CRITICALITY ignore  EXTENSION TransportLayerAddress     PRESENCE optional},
    ...
}

-- **************************************************************
--
-- RETRIEVE UE CONTEXT FAILURE
--
-- **************************************************************

RetrieveUEContextFailure ::= SEQUENCE {
    protocolIEs     ProtocolIE-Container    {{ RetrieveUEContextFailure-IEs}},
    ...
}

RetrieveUEContextFailure-IEs X2AP-PROTOCOL-IES ::= {
    { ID id-New-eNB-UE-X2AP-ID              CRITICALITY ignore  TYPE UE-X2AP-ID                 PRESENCE mandatory}|
    { ID id-New-eNB-UE-X2AP-ID-Extension    CRITICALITY ignore  TYPE UE-X2AP-ID-Extension       PRESENCE optional}|
    { ID id-Cause                           CRITICALITY ignore  TYPE Cause                      PRESENCE mandatory}|
    { ID id-CriticalityDiagnostics          CRITICALITY ignore  TYPE CriticalityDiagnostics     PRESENCE optional},
    ...
}

-- **************************************************************
--
-- SGNB ADDITION REQUEST
--
-- **************************************************************

SgNBAdditionRequest ::= SEQUENCE {
    protocolIEs     ProtocolIE-Container {{SgNBAdditionRequest-IEs}},
    ...
}

SgNBAdditionRequest-IEs X2AP-PROTOCOL-IES ::= {
    { ID id-MeNB-UE-X2AP-ID                         CRITICALITY reject  TYPE UE-X2AP-ID                                     PRESENCE mandatory}|
    { ID id-NRUESecurityCapabilities                    CRITICALITY reject  TYPE NRUESecurityCapabilities                   PRESENCE mandatory}|
    { ID id-SgNBSecurityKey                         CRITICALITY reject  TYPE SgNBSecurityKey                                    PRESENCE mandatory}|
    { ID id-SgNBUEAggregateMaximumBitRate           CRITICALITY reject  TYPE UEAggregateMaximumBitRate                  PRESENCE mandatory}|
    { ID id-SelectedPLMN                                CRITICALITY ignore  TYPE PLMN-Identity                                  PRESENCE optional}|
    { ID id-HandoverRestrictionList                 CRITICALITY ignore  TYPE HandoverRestrictionList                        PRESENCE optional}|
    { ID id-E-RABs-ToBeAdded-SgNBAddReqList         CRITICALITY reject  TYPE E-RABs-ToBeAdded-SgNBAddReqList            PRESENCE mandatory}|
    { ID id-MeNBtoSgNBContainer                     CRITICALITY reject  TYPE MeNBtoSgNBContainer                                PRESENCE mandatory}|
    { ID id-SgNB-UE-X2AP-ID                         CRITICALITY reject  TYPE SgNB-UE-X2AP-ID                                    PRESENCE optional}|
    { ID id-ExpectedUEBehaviour                     CRITICALITY ignore  TYPE ExpectedUEBehaviour                                PRESENCE optional}|
    { ID id-MeNB-UE-X2AP-ID-Extension               CRITICALITY reject  TYPE UE-X2AP-ID-Extension                           PRESENCE optional}|
    { ID id-RequestedSplitSRBs                      CRITICALITY reject  TYPE SplitSRBs                                      PRESENCE optional}|
    { ID id-MeNBResourceCoordinationInformation     CRITICALITY ignore  TYPE MeNBResourceCoordinationInformation        PRESENCE optional}|
    { ID id-SGNB-Addition-Trigger-Ind               CRITICALITY reject  TYPE SGNB-Addition-Trigger-Ind                  PRESENCE optional}|
    { ID id-SubscriberProfileIDforRFP               CRITICALITY ignore  TYPE SubscriberProfileIDforRFP                  PRESENCE optional}|
    { ID id-MeNBCell-ID                             CRITICALITY reject  TYPE ECGI                                           PRESENCE mandatory}|
    { ID id-DesiredActNotificationLevel             CRITICALITY ignore  TYPE DesiredActNotificationLevel                PRESENCE optional}|
    { ID id-TraceActivation                         CRITICALITY ignore  TYPE TraceActivation                                PRESENCE optional}|
    { ID id-LocationInformationSgNBReporting            CRITICALITY ignore  TYPE LocationInformationSgNBReporting           PRESENCE optional}|
    { ID id-Masked-IMEISV                           CRITICALITY ignore  TYPE Masked-IMEISV                                  PRESENCE optional}|
    { ID id-AdditionalRRMPriorityIndex              CRITICALITY ignore  TYPE AdditionalRRMPriorityIndex                 PRESENCE optional}|
    { ID id-RequestedFastMCGRecoveryViaSRB3         CRITICALITY ignore  TYPE     RequestedFastMCGRecoveryViaSRB3            PRESENCE optional}|
    { ID id-UEContextReferenceatSourceNGRAN         CRITICALITY ignore  TYPE RAN-UE-NGAP-ID                                 PRESENCE optional}|
    { ID id-ManagementBasedMDTallowed               CRITICALITY ignore  TYPE ManagementBasedMDTallowed                  PRESENCE optional }|
    { ID id-ManagementBasedMDTPLMNList              CRITICALITY ignore  TYPE MDTPLMNList                                    PRESENCE optional }|
    { ID id-UERadioCapabilityID                     CRITICALITY reject  TYPE UERadioCapabilityID                            PRESENCE optional}|
    { ID id-IABNodeIndication                       CRITICALITY reject  TYPE IABNodeIndication                              PRESENCE optional}|
    { ID id-sourceNG-RAN-node-id                    CRITICALITY ignore      TYPE Global-RAN-NODE-ID                         PRESENCE optional}|
    { ID id-UE-HistoryInformation                   CRITICALITY ignore  TYPE UE-HistoryInformation                      PRESENCE optional}|
    { ID id-UE-HistoryInformationFromTheUE          CRITICALITY ignore  TYPE UE-HistoryInformationFromTheUE             PRESENCE optional}|
    { ID id-PSCellChangeHistory             CRITICALITY ignore  TYPE PSCellChangeHistory                                PRESENCE optional}|
    { ID id-CHOinformation-AddReq                   CRITICALITY reject  TYPE CHOinformation-AddReq                      PRESENCE optional}|
    { ID id-SCGActivationRequest                    CRITICALITY ignore  TYPE SCGActivationRequest                           PRESENCE optional}|
    { ID id-CPAinformation-REQ                      CRITICALITY reject  TYPE CPAinformation-REQ                             PRESENCE optional}|
    { ID id-IABAuthorized                       CRITICALITY ignore  TYPE IABAuthorized                                  PRESENCE optional},
    ...
}

E-RABs-ToBeAdded-SgNBAddReqList ::= SEQUENCE (SIZE(1..maxnoofBearers)) OF ProtocolIE-Single-Container { {E-RABs-ToBeAdded-SgNBAddReq-ItemIEs} }

E-RABs-ToBeAdded-SgNBAddReq-ItemIEs X2AP-PROTOCOL-IES ::= {
    { ID id-E-RABs-ToBeAdded-SgNBAddReq-Item        CRITICALITY reject  TYPE E-RABs-ToBeAdded-SgNBAddReq-Item       PRESENCE mandatory},
    ...
}

E-RABs-ToBeAdded-SgNBAddReq-Item ::= SEQUENCE {
    e-RAB-ID                                E-RAB-ID,
    drb-ID                              DRB-ID,
    en-DC-ResourceConfiguration         EN-DC-ResourceConfiguration,
    resource-configuration              CHOICE {
        sgNBPDCPpresent                     E-RABs-ToBeAdded-SgNBAddReq-Item-SgNBPDCPpresent,
        sgNBPDCPnotpresent                  E-RABs-ToBeAdded-SgNBAddReq-Item-SgNBPDCPnotpresent,
        ...
    },
    iE-Extensions                   ProtocolExtensionContainer { {E-RABs-ToBeAdded-SgNBAddReq-ItemExtIEs} } OPTIONAL,
    ...
}

E-RABs-ToBeAdded-SgNBAddReq-ItemExtIEs X2AP-PROTOCOL-EXTENSION ::= {
    ...
}

E-RABs-ToBeAdded-SgNBAddReq-Item-SgNBPDCPpresent ::= SEQUENCE {
    full-E-RAB-Level-QoS-Parameters             E-RAB-Level-QoS-Parameters,
    max-MCG-admit-E-RAB-Level-QoS-Parameters    GBR-QosInformation                                                          OPTIONAL,
-- This IE shall be present if MCG resource and SCG resources IEs in the EN-DC Resource Configuration IE are set to “present” and GBR QoS Information IE is present in Full E-RAB Level QoS Parameters IE --
    dL-Forwarding                               DL-Forwarding                                                                       OPTIONAL,
    meNB-DL-GTP-TEIDatMCG                       GTPtunnelEndpoint                                                                   OPTIONAL,
-- This IE shall be present if MCG resource IE in the EN-DC Resource Configuration IE is set to “present” --
    s1-UL-GTPtunnelEndpoint                     GTPtunnelEndpoint,
    iE-Extensions                   ProtocolExtensionContainer { {E-RABs-ToBeAdded-SgNBAddReq-Item-SgNBPDCPpresentExtIEs} } OPTIONAL,
    ...
}

E-RABs-ToBeAdded-SgNBAddReq-Item-SgNBPDCPpresentExtIEs X2AP-PROTOCOL-EXTENSION ::= {
    { ID id-RLCMode-transferred                 CRITICALITY ignore  EXTENSION RLCMode                       PRESENCE optional}|
    { ID id-BearerType                          CRITICALITY ignore  EXTENSION BearerType                    PRESENCE optional}|
    { ID id-Ethernet-Type                       CRITICALITY ignore  EXTENSION Ethernet-Type                 PRESENCE optional}|
    { ID id-SourceDLForwardingIPAddress         CRITICALITY ignore  EXTENSION TransportLayerAddress     PRESENCE optional}|
    { ID id-SecurityIndication                  CRITICALITY reject  EXTENSION SecurityIndication            PRESENCE optional}|
    { ID id-SourceNodeDLForwardingIPAddress     CRITICALITY ignore  EXTENSION TransportLayerAddress     PRESENCE optional},
    ...
}

E-RABs-ToBeAdded-SgNBAddReq-Item-SgNBPDCPnotpresent ::= SEQUENCE {
    requested-SCG-E-RAB-Level-QoS-Parameters        E-RAB-Level-QoS-Parameters,
    meNB-UL-GTP-TEIDatPDCP                          GTPtunnelEndpoint,
    secondary-meNB-UL-GTP-TEIDatPDCP                GTPtunnelEndpoint   OPTIONAL,
    rlc-Mode                                        RLCMode,
    uL-Configuration                                ULConfiguration OPTIONAL,
-- This IE shall be present if MCG resource and SCG resources IEs in the EN-DC Resource Configuration IE are set to “present” --
    iE-Extensions                   ProtocolExtensionContainer { {E-RABs-ToBeAdded-SgNBAddReq-Item-SgNBPDCPnotpresentExtIEs} }       OPTIONAL,
    ...
}

E-RABs-ToBeAdded-SgNBAddReq-Item-SgNBPDCPnotpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-duplicationActivation                   CRITICALITY ignore  EXTENSION DuplicationActivation     PRESENCE optional},
    ...
}

-- **************************************************************
--
-- SGNB ADDITION REQUEST ACKNOWLEDGE
--
-- **************************************************************

SgNBAdditionRequestAcknowledge ::= SEQUENCE {
    protocolIEs     ProtocolIE-Container    {{SgNBAdditionRequestAcknowledge-IEs}},
    ...
}

SgNBAdditionRequestAcknowledge-IEs X2AP-PROTOCOL-IES ::= {
    { ID id-MeNB-UE-X2AP-ID                             CRITICALITY reject  TYPE UE-X2AP-ID                                                 PRESENCE mandatory}|
    { ID id-SgNB-UE-X2AP-ID                             CRITICALITY reject  TYPE SgNB-UE-X2AP-ID                                            PRESENCE mandatory}|
    { ID id-E-RABs-Admitted-ToBeAdded-SgNBAddReqAckList CRITICALITY ignore  TYPE E-RABs-Admitted-ToBeAdded-SgNBAddReqAckList        PRESENCE mandatory}|
    { ID id-E-RABs-NotAdmitted-List                     CRITICALITY ignore  TYPE E-RAB-List                                                 PRESENCE optional}|
    { ID id-SgNBtoMeNBContainer                         CRITICALITY reject  TYPE SgNBtoMeNBContainer                                        PRESENCE mandatory}|
    { ID id-CriticalityDiagnostics                      CRITICALITY ignore  TYPE CriticalityDiagnostics                                 PRESENCE optional}|
    { ID id-MeNB-UE-X2AP-ID-Extension                   CRITICALITY reject  TYPE UE-X2AP-ID-Extension                                   PRESENCE optional}|
    { ID id-AdmittedSplitSRBs                           CRITICALITY reject  TYPE SplitSRBs                                                  PRESENCE optional}|
    { ID id-SgNBResourceCoordinationInformation         CRITICALITY ignore  TYPE SgNBResourceCoordinationInformation                PRESENCE optional}|
    { ID id-RRCConfigIndication                         CRITICALITY reject  TYPE RRC-Config-Ind                                             PRESENCE optional}|
    { ID id-LocationInformationSgNB                     CRITICALITY ignore  TYPE LocationInformationSgNB                                PRESENCE optional}|
    { ID id-AvailableFastMCGRecoveryViaSRB3             CRITICALITY ignore  TYPE AvailableFastMCGRecoveryViaSRB3                        PRESENCE optional }|
    { ID id-DirectForwardingPathAvailability            CRITICALITY ignore  TYPE DirectForwardingPathAvailability                   PRESENCE optional }|
    { ID id-SCGActivationStatus                         CRITICALITY ignore  TYPE SCGActivationStatus                                        PRESENCE optional}|
    { ID id-CPAinformation-REQ-ACK                      CRITICALITY ignore  TYPE CPAinformation-REQ-ACK                                 PRESENCE optional},
    ...
}

E-RABs-Admitted-ToBeAdded-SgNBAddReqAckList ::= SEQUENCE (SIZE (1..maxnoofBearers)) OF ProtocolIE-Single-Container { {E-RABs-Admitted-ToBeAdded-SgNBAddReqAck-ItemIEs} }

E-RABs-Admitted-ToBeAdded-SgNBAddReqAck-ItemIEs X2AP-PROTOCOL-IES ::= {
    { ID id-E-RABs-Admitted-ToBeAdded-SgNBAddReqAck-Item    CRITICALITY ignore  TYPE E-RABs-Admitted-ToBeAdded-SgNBAddReqAck-Item       PRESENCE mandatory}
}

E-RABs-Admitted-ToBeAdded-SgNBAddReqAck-Item ::= SEQUENCE {
    e-RAB-ID                            E-RAB-ID,
    en-DC-ResourceConfiguration         EN-DC-ResourceConfiguration,
    resource-configuration              CHOICE {
        sgNBPDCPpresent                     E-RABs-Admitted-ToBeAdded-SgNBAddReqAck-Item-SgNBPDCPpresent,
        sgNBPDCPnotpresent                  E-RABs-Admitted-ToBeAdded-SgNBAddReqAck-Item-SgNBPDCPnotpresent,
        ...
    },
    iE-Extensions                   ProtocolExtensionContainer { {E-RABs-ToBeAdded-SgNBAddReqAck-ItemExtIEs} }  OPTIONAL,
    ...
}

E-RABs-ToBeAdded-SgNBAddReqAck-ItemExtIEs X2AP-PROTOCOL-EXTENSION ::= {
    ...
}

E-RABs-Admitted-ToBeAdded-SgNBAddReqAck-Item-SgNBPDCPpresent ::= SEQUENCE {
    s1-DL-GTPtunnelEndpoint                 GTPtunnelEndpoint,
    sgNB-UL-GTP-TEIDatPDCP                  GTPtunnelEndpoint                                                                                       OPTIONAL,
-- This IE shall be present if MCG resource IE in the EN-DC Resource Configuration IE is set to “present” --
    rlc-Mode                                RLCMode                                                                                                 OPTIONAL,
-- This IE shall be present if MCG resource IE in the EN-DC Resource Configuration IE is set to “present” --
    dL-Forwarding-GTPtunnelEndpoint         GTPtunnelEndpoint                                                                                       OPTIONAL,
    uL-Forwarding-GTPtunnelEndpoint         GTPtunnelEndpoint                                                                                       OPTIONAL,
    mCG-E-RAB-Level-QoS-Parameters          E-RAB-Level-QoS-Parameters                                                                              OPTIONAL,
-- This IE shall be present if MCG resource and SCG resource IEs in the EN-DC Resource Configuration IE are set to “present” and the GBR QoS Information IE is present in the Requested MCG E-RAB Level QoS Parameters IE --
    uL-Configuration                            ULConfiguration                                                                                         OPTIONAL,
-- This IE shall be present if MCG resource and SCG resources IEs in the EN-DC Resource Configuration IE are set to “present” --
    iE-Extensions                           ProtocolExtensionContainer { {E-RABs-Admitted-ToBeAdded-SgNBAddReqAck-Item-SgNBPDCPpresentExtIEs} }         OPTIONAL,
    ...
}

E-RABs-Admitted-ToBeAdded-SgNBAddReqAck-Item-SgNBPDCPpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-SourceDLForwardingIPAddress         CRITICALITY ignore  EXTENSION TransportLayerAddress     PRESENCE optional}|
    { ID id-SecurityResult                          CRITICALITY ignore  EXTENSION SecurityResult                    PRESENCE optional},
    ...
}

E-RABs-Admitted-ToBeAdded-SgNBAddReqAck-Item-SgNBPDCPnotpresent ::= SEQUENCE {
    sgNB-DL-GTP-TEIDatSCG               GTPtunnelEndpoint,
    secondary-sgNB-DL-GTP-TEIDatSCG     GTPtunnelEndpoint       OPTIONAL,
    iE-Extensions                       ProtocolExtensionContainer { {E-RABs-Admitted-ToBeAdded-SgNBAddReqAck-Item-SgNBPDCPnotpresentExtIEs} }      OPTIONAL,
    ...
}

E-RABs-Admitted-ToBeAdded-SgNBAddReqAck-Item-SgNBPDCPnotpresentExtIEs X2AP-PROTOCOL-EXTENSION ::= {
    { ID id-lCID                CRITICALITY ignore  EXTENSION LCID          PRESENCE optional},
    ...
}



-- **************************************************************
--
-- SGNB ADDITION REQUEST REJECT
--
-- **************************************************************

SgNBAdditionRequestReject ::= SEQUENCE {
    protocolIEs     ProtocolIE-Container    {{SgNBAdditionRequestReject-IEs}},
    ...
}

SgNBAdditionRequestReject-IEs X2AP-PROTOCOL-IES ::= {
    { ID id-MeNB-UE-X2AP-ID                 CRITICALITY reject  TYPE UE-X2AP-ID                 PRESENCE mandatory}|
    { ID id-SgNB-UE-X2AP-ID                 CRITICALITY reject  TYPE SgNB-UE-X2AP-ID            PRESENCE optional}|
    { ID id-Cause                           CRITICALITY ignore  TYPE Cause                      PRESENCE mandatory}|
    { ID id-CriticalityDiagnostics          CRITICALITY ignore  TYPE CriticalityDiagnostics     PRESENCE optional}|
    { ID id-MeNB-UE-X2AP-ID-Extension       CRITICALITY reject  TYPE UE-X2AP-ID-Extension       PRESENCE optional},
    ...
}


-- **************************************************************
--
-- SGNB RECONFIGURATION COMPLETE
--
-- **************************************************************

SgNBReconfigurationComplete ::= SEQUENCE {
    protocolIEs     ProtocolIE-Container    {{SgNBReconfigurationComplete-IEs}},
    ...
}

SgNBReconfigurationComplete-IEs X2AP-PROTOCOL-IES ::= {
    { ID id-MeNB-UE-X2AP-ID                         CRITICALITY reject  TYPE UE-X2AP-ID                                         PRESENCE mandatory}|
    { ID id-SgNB-UE-X2AP-ID                         CRITICALITY reject  TYPE SgNB-UE-X2AP-ID                                    PRESENCE mandatory}|
    { ID id-ResponseInformationSgNBReconfComp       CRITICALITY ignore  TYPE ResponseInformationSgNBReconfComp          PRESENCE mandatory}|
    { ID id-MeNB-UE-X2AP-ID-Extension               CRITICALITY reject  TYPE UE-X2AP-ID-Extension                               PRESENCE optional},
    ...
}

ResponseInformationSgNBReconfComp ::= CHOICE {
    success-SgNBReconfComp              ResponseInformationSgNBReconfComp-SuccessItem,
    reject-by-MeNB-SgNBReconfComp       ResponseInformationSgNBReconfComp-RejectByMeNBItem,
    ...
}

ResponseInformationSgNBReconfComp-SuccessItem ::= SEQUENCE {
    meNBtoSgNBContainer             MeNBtoSgNBContainer                 OPTIONAL,
    iE-Extensions                   ProtocolExtensionContainer { {ResponseInformationSgNBReconfComp-SuccessItemExtIEs} }    OPTIONAL,
    ...
}

ResponseInformationSgNBReconfComp-SuccessItemExtIEs X2AP-PROTOCOL-EXTENSION ::= {
    ...
}

ResponseInformationSgNBReconfComp-RejectByMeNBItem ::= SEQUENCE {
    cause                           Cause,
    iE-Extensions                   ProtocolExtensionContainer { {ResponseInformationSgNBReconfComp-RejectByMeNBItemExtIEs} }       OPTIONAL,
    ...
}

ResponseInformationSgNBReconfComp-RejectByMeNBItemExtIEs X2AP-PROTOCOL-EXTENSION ::= {
    ...
}


-- **************************************************************
--
-- SGNB MODIFICATION REQUEST
--
-- **************************************************************

SgNBModificationRequest ::= SEQUENCE {
    protocolIEs     ProtocolIE-Container    {{ SgNBModificationRequest-IEs}},
    ...
}

SgNBModificationRequest-IEs X2AP-PROTOCOL-IES ::= {
    { ID id-MeNB-UE-X2AP-ID                         CRITICALITY reject  TYPE UE-X2AP-ID                                         PRESENCE mandatory}|
    { ID id-SgNB-UE-X2AP-ID                         CRITICALITY reject  TYPE SgNB-UE-X2AP-ID                                    PRESENCE mandatory}|
    { ID id-Cause                                   CRITICALITY ignore  TYPE Cause                                              PRESENCE mandatory}|
    { ID id-SelectedPLMN                            CRITICALITY ignore  TYPE PLMN-Identity                                      PRESENCE optional}|
    { ID id-HandoverRestrictionList                 CRITICALITY ignore  TYPE HandoverRestrictionList                            PRESENCE optional}|
    { ID    id-SCGConfigurationQuery                CRITICALITY ignore  TYPE SCGConfigurationQuery                          PRESENCE optional}|
    { ID id-UE-ContextInformation-SgNBModReq        CRITICALITY reject  TYPE UE-ContextInformation-SgNBModReq               PRESENCE optional}|
    { ID id-MeNBtoSgNBContainer                     CRITICALITY reject  TYPE MeNBtoSgNBContainer                                PRESENCE optional}|
    { ID id-MeNB-UE-X2AP-ID-Extension               CRITICALITY reject  TYPE UE-X2AP-ID-Extension                               PRESENCE optional}|
    { ID id-MeNBResourceCoordinationInformation     CRITICALITY ignore  TYPE MeNBResourceCoordinationInformation            PRESENCE optional}|
    { ID id-RequestedSplitSRBs                      CRITICALITY ignore  TYPE SplitSRBs                                          PRESENCE optional}|
    { ID id-RequestedSplitSRBsrelease               CRITICALITY ignore  TYPE SplitSRBs                                          PRESENCE optional}|
    { ID id-DesiredActNotificationLevel             CRITICALITY ignore  TYPE DesiredActNotificationLevel                    PRESENCE optional}|
    { ID id-LocationInformationSgNBReporting        CRITICALITY ignore  TYPE LocationInformationSgNBReporting               PRESENCE optional}|
    { ID id-MeNBCell-ID                             CRITICALITY ignore  TYPE ECGI                                               PRESENCE optional}|
    { ID id-RequestedFastMCGRecoveryViaSRB3         CRITICALITY ignore  TYPE RequestedFastMCGRecoveryViaSRB3                PRESENCE optional}|
    { ID id-RequestedFastMCGRecoveryViaSRB3Release  CRITICALITY ignore  TYPE RequestedFastMCGRecoveryViaSRB3Release     PRESENCE optional}|
    { ID id-SNtriggered                             CRITICALITY ignore  TYPE SNtriggered                                        PRESENCE optional}|
    { ID id-IABNodeIndication                       CRITICALITY reject  TYPE IABNodeIndication                                  PRESENCE optional}|
    { ID id-PSCellHistoryInformationRetrieve        CRITICALITY ignore  TYPE PSCellHistoryInformationRetrieve               PRESENCE optional}|
    { ID id-UE-HistoryInformationFromTheUE          CRITICALITY ignore  TYPE UE-HistoryInformationFromTheUE             PRESENCE optional}|
    { ID id-CHOinformation-ModReq                   CRITICALITY ignore  TYPE CHOinformation-ModReq                          PRESENCE optional}|
    { ID id-SCGActivationRequest                    CRITICALITY ignore  TYPE SCGActivationRequest                               PRESENCE optional}|
    { ID id-CPAinformation-MOD                      CRITICALITY ignore  TYPE CPAinformation-MOD                                 PRESENCE optional}|
    { ID id-CPCupdate-MOD                           CRITICALITY ignore  TYPE CPCupdate-MOD                                      PRESENCE optional}|
    { ID id-IABAuthorized                       CRITICALITY ignore  TYPE IABAuthorized                                  PRESENCE optional},
    ...
}

UE-ContextInformation-SgNBModReq ::= SEQUENCE {
    nRUE-SecurityCapabilities       NRUESecurityCapabilities                                                            OPTIONAL,
    sgNB-SecurityKey                SgNBSecurityKey                                                                     OPTIONAL,
    sgNBUEAggregateMaximumBitRate   UEAggregateMaximumBitRate                                                           OPTIONAL,
    e-RABs-ToBeAdded                E-RABs-ToBeAdded-SgNBModReq-List                                                    OPTIONAL,
    e-RABs-ToBeModified             E-RABs-ToBeModified-SgNBModReq-List                                                 OPTIONAL,
    e-RABs-ToBeReleased             E-RABs-ToBeReleased-SgNBModReq-List                                                 OPTIONAL,
    iE-Extensions                   ProtocolExtensionContainer { {UE-ContextInformationSgNBModReqExtIEs} }          OPTIONAL,
    ...
}

UE-ContextInformationSgNBModReqExtIEs X2AP-PROTOCOL-EXTENSION ::= {
    {   ID id-SubscriberProfileIDforRFP                 CRITICALITY ignore  EXTENSION SubscriberProfileIDforRFP                                 PRESENCE optional}|
    { ID id-AdditionalRRMPriorityIndex              CRITICALITY ignore  EXTENSION AdditionalRRMPriorityIndex                    PRESENCE optional}|
    {ID id-LowerLayerPresenceStatusChange           CRITICALITY ignore  EXTENSION LowerLayerPresenceStatusChange                PRESENCE optional},
    ...
}

E-RABs-ToBeAdded-SgNBModReq-List ::= SEQUENCE (SIZE(1..maxnoofBearers)) OF ProtocolIE-Single-Container { {E-RABs-ToBeAdded-SgNBModReq-ItemIEs} }

E-RABs-ToBeAdded-SgNBModReq-ItemIEs X2AP-PROTOCOL-IES ::= {
    { ID id-E-RABs-ToBeAdded-SgNBModReq-Item        CRITICALITY ignore  TYPE E-RABs-ToBeAdded-SgNBModReq-Item       PRESENCE mandatory},
    ...
}

E-RABs-ToBeAdded-SgNBModReq-Item ::= SEQUENCE {
    e-RAB-ID                                E-RAB-ID,
    drb-ID                                  DRB-ID,
    en-DC-ResourceConfiguration             EN-DC-ResourceConfiguration,
    resource-configuration                  CHOICE {
        sgNBPDCPpresent                     E-RABs-ToBeAdded-SgNBModReq-Item-SgNBPDCPpresent,
        sgNBPDCPnotpresent                  E-RABs-ToBeAdded-SgNBModReq-Item-SgNBPDCPnotpresent,
        ...
    },
    iE-Extensions                   ProtocolExtensionContainer { {E-RABs-ToBeAdded-SgNBModReq-ItemExtIEs} } OPTIONAL,
    ...
}

E-RABs-ToBeAdded-SgNBModReq-ItemExtIEs X2AP-PROTOCOL-EXTENSION ::= {
    ...
}

E-RABs-ToBeAdded-SgNBModReq-Item-SgNBPDCPpresent ::= SEQUENCE {
    full-E-RAB-Level-QoS-Parameters         E-RAB-Level-QoS-Parameters,
    max-MN-admit-E-RAB-Level-QoS-Parameters GBR-QosInformation                                                          OPTIONAL,
-- This IE shall be present if MCG resource and SCG resources IEs in the EN-DC Resource Configuration IE are set to “present” and GBR QoS Information IE is present in Full E-RAB Level QoS Parameters IE --
    dL-Forwarding                           DL-Forwarding                                                                       OPTIONAL,
    meNB-DL-GTP-TEIDatMCG                   GTPtunnelEndpoint                                                                   OPTIONAL,
-- This IE shall be present if MCG resource IE in the EN-DC Resource Configuration IE is set to “present” --
    s1-UL-GTPtunnelEndpoint                 GTPtunnelEndpoint,
    iE-Extensions                   ProtocolExtensionContainer { {E-RABs-ToBeAdded-SgNBModReq-Item-SgNBPDCPpresentExtIEs} }     OPTIONAL,
    ...
}

E-RABs-ToBeAdded-SgNBModReq-Item-SgNBPDCPpresentExtIEs X2AP-PROTOCOL-EXTENSION ::= {
    { ID id-RLCMode-transferred                 CRITICALITY ignore  EXTENSION RLCMode                   PRESENCE optional}|
    { ID id-BearerType                          CRITICALITY ignore  EXTENSION BearerType                PRESENCE optional}|
    { ID id-Ethernet-Type                       CRITICALITY ignore  EXTENSION Ethernet-Type             PRESENCE optional}|
    { ID id-SecurityIndication                  CRITICALITY reject  EXTENSION SecurityIndication        PRESENCE optional}|
    { ID id-SourceDLForwardingIPAddress         CRITICALITY ignore  EXTENSION TransportLayerAddress PRESENCE optional},
    ...
}

E-RABs-ToBeAdded-SgNBModReq-Item-SgNBPDCPnotpresent ::= SEQUENCE {
    requested-SCG-E-RAB-Level-QoS-Parameters        E-RAB-Level-QoS-Parameters,
    meNB-UL-GTP-TEIDatPDCP                          GTPtunnelEndpoint,
    secondary-meNB-UL-GTP-TEIDatPDCP                GTPtunnelEndpoint       OPTIONAL,
    rlc-Mode                                        RLCMode,
    uL-Configuration                                ULConfiguration                                                             OPTIONAL,
-- This IE shall be present if MCG resource and SCG resources IEs in the EN-DC Resource Configuration IE are set to “present” --
    iE-Extensions                   ProtocolExtensionContainer { {E-RABs-ToBeAdded-SgNBModReq-Item-SgNBPDCPnotpresentExtIEs} }      OPTIONAL,
    ...
}

E-RABs-ToBeAdded-SgNBModReq-Item-SgNBPDCPnotpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-duplicationActivation                   CRITICALITY ignore  EXTENSION DuplicationActivation     PRESENCE optional},
    ...
}


E-RABs-ToBeModified-SgNBModReq-List ::= SEQUENCE (SIZE(1..maxnoofBearers)) OF ProtocolIE-Single-Container { {E-RABs-ToBeModified-SgNBModReq-ItemIEs} }

E-RABs-ToBeModified-SgNBModReq-ItemIEs X2AP-PROTOCOL-IES ::= {
    { ID id-E-RABs-ToBeModified-SgNBModReq-Item CRITICALITY ignore  TYPE E-RABs-ToBeModified-SgNBModReq-Item        PRESENCE mandatory},
    ...
}


E-RABs-ToBeModified-SgNBModReq-Item ::= SEQUENCE {
    e-RAB-ID                                E-RAB-ID,
    en-DC-ResourceConfiguration         EN-DC-ResourceConfiguration,
    resource-configuration              CHOICE {
        sgNBPDCPpresent                     E-RABs-ToBeModified-SgNBModReq-Item-SgNBPDCPpresent,
        sgNBPDCPnotpresent                  E-RABs-ToBeModified-SgNBModReq-Item-SgNBPDCPnotpresent,
        ...
    },
    iE-Extensions                   ProtocolExtensionContainer { {E-RABs-ToBeModified-SgNBModReq-ItemExtIEs} }  OPTIONAL,
    ...
}

E-RABs-ToBeModified-SgNBModReq-ItemExtIEs X2AP-PROTOCOL-EXTENSION ::= {
    ...
}

E-RABs-ToBeModified-SgNBModReq-Item-SgNBPDCPpresent ::= SEQUENCE {
    full-E-RAB-Level-QoS-Parameters         E-RAB-Level-QoS-Parameters                                                                      OPTIONAL,
    max-MN-admit-E-RAB-Level-QoS-Parameters GBR-QosInformation                                                                              OPTIONAL,
    meNB-DL-GTP-TEIDatMCG                   GTPtunnelEndpoint                                                                               OPTIONAL,
    s1-UL-GTPtunnelEndpoint                 GTPtunnelEndpoint                                                                               OPTIONAL,
    iE-Extensions                   ProtocolExtensionContainer { {E-RABs-ToBeModified-SgNBModReq-Item-SgNBPDCPpresentExtIEs} }  OPTIONAL,
    ...
}

E-RABs-ToBeModified-SgNBModReq-Item-SgNBPDCPpresentExtIEs X2AP-PROTOCOL-EXTENSION ::= {
    { ID id-RLC-Status          CRITICALITY ignore          EXTENSION RLC-Status                PRESENCE optional },
    ...
}

E-RABs-ToBeModified-SgNBModReq-Item-SgNBPDCPnotpresent ::= SEQUENCE {
    requested-SCG-E-RAB-Level-QoS-Parameters        E-RAB-Level-QoS-Parameters                                                                          OPTIONAL,
    meNB-UL-GTP-TEIDatPDCP                      GTPtunnelEndpoint                                                                                   OPTIONAL,
    uL-Configuration                                ULConfiguration                                                                                     OPTIONAL,
    iE-Extensions                   ProtocolExtensionContainer { {E-RABs-ToBeModified-SgNBModReq-Item-SgNBPDCPnotpresentExtIEs} }   OPTIONAL,
    ...
}

E-RABs-ToBeModified-SgNBModReq-Item-SgNBPDCPnotpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-secondarymeNBULGTPTEIDatPDCP            CRITICALITY ignore  EXTENSION GTPtunnelEndpoint         PRESENCE optional},
    ...
}

E-RABs-ToBeReleased-SgNBModReq-List ::= SEQUENCE (SIZE(1..maxnoofBearers)) OF ProtocolIE-Single-Container { {E-RABs-ToBeReleased-SgNBModReq-ItemIEs} }

E-RABs-ToBeReleased-SgNBModReq-ItemIEs X2AP-PROTOCOL-IES ::= {
    { ID id-E-RABs-ToBeReleased-SgNBModReq-Item CRITICALITY ignore  TYPE E-RABs-ToBeReleased-SgNBModReq-Item        PRESENCE mandatory},
    ...
}

E-RABs-ToBeReleased-SgNBModReq-Item ::= SEQUENCE {
    e-RAB-ID                                E-RAB-ID,
    en-DC-ResourceConfiguration         EN-DC-ResourceConfiguration,
    resource-configuration              CHOICE {
        sgNBPDCPpresent                     E-RABs-ToBeReleased-SgNBModReq-Item-SgNBPDCPpresent,
        sgNBPDCPnotpresent                  E-RABs-ToBeReleased-SgNBModReq-Item-SgNBPDCPnotpresent,
        ...
    },
    iE-Extensions                   ProtocolExtensionContainer { {E-RABs-ToBeReleased-SgNBModReq-ItemExtIEs} }  OPTIONAL,
    ...
}

E-RABs-ToBeReleased-SgNBModReq-ItemExtIEs X2AP-PROTOCOL-EXTENSION ::= {
    ...
}

E-RABs-ToBeReleased-SgNBModReq-Item-SgNBPDCPpresent ::= SEQUENCE {
    dL-GTPtunnelEndpoint            GTPtunnelEndpoint                                                                               OPTIONAL,
    uL-GTPtunnelEndpoint            GTPtunnelEndpoint                                                                               OPTIONAL,
    iE-Extensions               ProtocolExtensionContainer { {E-RABs-ToBeReleased-SgNBModReq-Item-SgNBPDCPpresentExtIEs} }  OPTIONAL,
    ...
}

E-RABs-ToBeReleased-SgNBModReq-Item-SgNBPDCPpresentExtIEs X2AP-PROTOCOL-EXTENSION ::= {
    ...
}

E-RABs-ToBeReleased-SgNBModReq-Item-SgNBPDCPnotpresent ::= SEQUENCE {
    iE-Extensions                   ProtocolExtensionContainer { {E-RABs-ToBeReleased-SgNBModReq-Item-SgNBPDCPnotpresentExtIEs} }   OPTIONAL,
    ...
}

E-RABs-ToBeReleased-SgNBModReq-Item-SgNBPDCPnotpresentExtIEs X2AP-PROTOCOL-EXTENSION ::= {
    ...
}



-- **************************************************************
--
-- SGNB MODIFICATION REQUEST ACKNOWLEDGE
--
-- **************************************************************

SgNBModificationRequestAcknowledge ::= SEQUENCE {
    protocolIEs     ProtocolIE-Container    {{SgNBModificationRequestAcknowledge-IEs}},
    ...
}

SgNBModificationRequestAcknowledge-IEs X2AP-PROTOCOL-IES ::= {
    { ID id-MeNB-UE-X2AP-ID                             CRITICALITY ignore  TYPE UE-X2AP-ID                                                 PRESENCE mandatory}|
    { ID id-SgNB-UE-X2AP-ID                             CRITICALITY ignore  TYPE SgNB-UE-X2AP-ID                                                PRESENCE mandatory}|
    { ID id-E-RABs-Admitted-ToBeAdded-SgNBModAckList        CRITICALITY ignore  TYPE E-RABs-Admitted-ToBeAdded-SgNBModAckList           PRESENCE optional}|
    { ID id-E-RABs-Admitted-ToBeModified-SgNBModAckList CRITICALITY ignore  TYPE E-RABs-Admitted-ToBeModified-SgNBModAckList        PRESENCE optional}|
    { ID id-E-RABs-Admitted-ToBeReleased-SgNBModAckList CRITICALITY ignore  TYPE E-RABs-Admitted-ToBeReleased-SgNBModAckList        PRESENCE optional}|
    { ID id-E-RABs-NotAdmitted-List                     CRITICALITY ignore  TYPE E-RAB-List                                                 PRESENCE optional}|
    { ID id-SgNBtoMeNBContainer                         CRITICALITY ignore  TYPE SgNBtoMeNBContainer                                        PRESENCE optional}|
    { ID id-CriticalityDiagnostics                      CRITICALITY ignore  TYPE CriticalityDiagnostics                                 PRESENCE optional}|
    { ID id-MeNB-UE-X2AP-ID-Extension                   CRITICALITY ignore  TYPE UE-X2AP-ID-Extension                                   PRESENCE optional}|
    { ID id-SgNBResourceCoordinationInformation         CRITICALITY ignore  TYPE SgNBResourceCoordinationInformation                PRESENCE optional}|
    { ID id-AdmittedSplitSRBs                           CRITICALITY ignore  TYPE SplitSRBs                                                  PRESENCE optional}|
    { ID id-AdmittedSplitSRBsrelease                        CRITICALITY ignore  TYPE SplitSRBs                                                  PRESENCE optional}|
    { ID id-RRCConfigIndication                         CRITICALITY reject  TYPE RRC-Config-Ind                                             PRESENCE optional}|
    { ID id-LocationInformationSgNB                     CRITICALITY ignore  TYPE LocationInformationSgNB                                PRESENCE optional}|
    { ID id-AvailableFastMCGRecoveryViaSRB3             CRITICALITY ignore  TYPE AvailableFastMCGRecoveryViaSRB3                        PRESENCE optional}|
    { ID id-ReleaseFastMCGRecoveryViaSRB3       CRITICALITY ignore  TYPE ReleaseFastMCGRecoveryViaSRB3                                  PRESENCE optional}|
    { ID id-SCG-UE-HistoryInformation                   CRITICALITY ignore  TYPE SCG-UE-HistoryInformation                          PRESENCE optional}|
    { ID id-SCGActivationStatus                         CRITICALITY ignore  TYPE SCGActivationStatus                                        PRESENCE optional}|
    { ID id-CPAinformation-MOD-ACK                      CRITICALITY reject  TYPE CPAinformation-MOD-ACK                                 PRESENCE optional},
    ...
}

E-RABs-Admitted-ToBeAdded-SgNBModAckList ::= SEQUENCE (SIZE (1..maxnoofBearers)) OF ProtocolIE-Single-Container { {E-RABs-Admitted-ToBeAdded-SgNBModAck-ItemIEs} }

E-RABs-Admitted-ToBeAdded-SgNBModAck-ItemIEs X2AP-PROTOCOL-IES ::= {
    { ID id-E-RABs-Admitted-ToBeAdded-SgNBModAck-Item   CRITICALITY ignore  TYPE E-RABs-Admitted-ToBeAdded-SgNBModAck-Item      PRESENCE mandatory}
}

E-RABs-Admitted-ToBeAdded-SgNBModAck-Item ::= SEQUENCE {
    e-RAB-ID                                E-RAB-ID,
    en-DC-ResourceConfiguration         EN-DC-ResourceConfiguration,
    resource-configuration              CHOICE {
        sgNBPDCPpresent                     E-RABs-Admitted-ToBeAdded-SgNBModAck-Item-SgNBPDCPpresent,
        sgNBPDCPnotpresent                  E-RABs-Admitted-ToBeAdded-SgNBModAck-Item-SgNBPDCPnotpresent,
        ...
    },
    iE-Extensions                   ProtocolExtensionContainer { {E-RABs-Admitted-ToBeAdded-SgNBModAck-ItemExtIEs} }    OPTIONAL,
    ...
}

E-RABs-Admitted-ToBeAdded-SgNBModAck-ItemExtIEs X2AP-PROTOCOL-EXTENSION ::= {
    ...
}

E-RABs-Admitted-ToBeAdded-SgNBModAck-Item-SgNBPDCPpresent ::= SEQUENCE {
    s1-DL-GTPtunnelEndpoint                 GTPtunnelEndpoint,
    sgNB-UL-GTP-TEIDatPDCP                  GTPtunnelEndpoint                                                                                   OPTIONAL,
-- This IE shall be present if MCG resource IE in the EN-DC Resource Configuration IE are set to “present” --
    rlc-Mode                                    RLCMode                                                                                             OPTIONAL,
-- This IE shall be present if MCG resource IE in the EN-DC Resource Configuration IE are set to “present” --
    dL-Forwarding-GTPtunnelEndpoint         GTPtunnelEndpoint                                                                                   OPTIONAL,
    uL-Forwarding-GTPtunnelEndpoint         GTPtunnelEndpoint                                                                                   OPTIONAL,
    mCG-E-RAB-Level-QoS-Parameters          E-RAB-Level-QoS-Parameters                                                                          OPTIONAL,
-- This IE shall be present if MCG resource and SCG resource IEs in the EN-DC Resource Configuration IE are set to “present” and the GBR QoS Information IE is present in the Requested MCG E-RAB Level QoS Parameters IE --
    uL-Configuration                        ULConfiguration                                                                                         OPTIONAL,
-- This IE shall be present if MCG resource and SCG resources IEs in the EN-DC Resource Configuration IE are set to “present” --
    iE-Extensions                   ProtocolExtensionContainer { {E-RABs-Admitted-ToBeAdded-SgNBModAck-Item-SgNBPDCPpresentExtIEs} }        OPTIONAL,
    ...
}

E-RABs-Admitted-ToBeAdded-SgNBModAck-Item-SgNBPDCPpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-SecurityResult                          CRITICALITY ignore  EXTENSION SecurityResult                PRESENCE optional}|
    { ID id-SourceDLForwardingIPAddress             CRITICALITY ignore  EXTENSION TransportLayerAddress     PRESENCE optional},
    ...
}

E-RABs-Admitted-ToBeAdded-SgNBModAck-Item-SgNBPDCPnotpresent ::= SEQUENCE {
    sgNB-DL-GTP-TEIDatSCG                   GTPtunnelEndpoint,
    secondary-sgNB-DL-GTP-TEIDatSCG         GTPtunnelEndpoint           OPTIONAL,
    iE-Extensions                   ProtocolExtensionContainer { {E-RABs-Admitted-ToBeAdded-SgNBModAck-Item-SgNBPDCPnotpresentExtIEs} } OPTIONAL,
    ...
}

E-RABs-Admitted-ToBeAdded-SgNBModAck-Item-SgNBPDCPnotpresentExtIEs X2AP-PROTOCOL-EXTENSION ::= {
    {ID id-lCID             CRITICALITY ignore  EXTENSION LCID      PRESENCE optional},
    ...
}

E-RABs-Admitted-ToBeModified-SgNBModAckList ::= SEQUENCE (SIZE (1..maxnoofBearers)) OF ProtocolIE-Single-Container { {E-RABs-Admitted-ToBeModified-SgNBModAck-ItemIEs} }

E-RABs-Admitted-ToBeModified-SgNBModAck-ItemIEs X2AP-PROTOCOL-IES ::= {
    { ID id-E-RABs-Admitted-ToBeModified-SgNBModAck-Item        CRITICALITY ignore  TYPE E-RABs-Admitted-ToBeModified-SgNBModAck-Item       PRESENCE mandatory}
}

E-RABs-Admitted-ToBeModified-SgNBModAck-Item ::= SEQUENCE {
    e-RAB-ID                                E-RAB-ID,
    en-DC-ResourceConfiguration         EN-DC-ResourceConfiguration,
    resource-configuration              CHOICE {
        sgNBPDCPpresent                     E-RABs-Admitted-ToBeModified-SgNBModAck-Item-SgNBPDCPpresent,
        sgNBPDCPnotpresent                  E-RABs-Admitted-ToBeModified-SgNBModAck-Item-SgNBPDCPnotpresent,
        ...
    },
    iE-Extensions                   ProtocolExtensionContainer { {E-RABs-ToBeAdded-SgNBModAck-ItemExtIEs} } OPTIONAL,
    ...
}

E-RABs-ToBeAdded-SgNBModAck-ItemExtIEs X2AP-PROTOCOL-EXTENSION ::= {
    ...
}

E-RABs-Admitted-ToBeModified-SgNBModAck-Item-SgNBPDCPpresent ::= SEQUENCE {
    s1-DL-GTPtunnelEndpoint                 GTPtunnelEndpoint                                                                                       OPTIONAL,
    sgNB-UL-GTP-TEIDatPDCP                  GTPtunnelEndpoint                                                                                       OPTIONAL,
    mCG-E-RAB-Level-QoS-Parameters          E-RAB-Level-QoS-Parameters                                                                              OPTIONAL,
    uL-Configuration                            ULConfiguration                                                                                         OPTIONAL,
    iE-Extensions                   ProtocolExtensionContainer { {E-RABs-Admitted-ToBeModified-SgNBModAck-Item-SgNBPDCPpresentExtIEs} }     OPTIONAL,
    ...
}

E-RABs-Admitted-ToBeModified-SgNBModAck-Item-SgNBPDCPpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional},
    ...
}

E-RABs-Admitted-ToBeModified-SgNBModAck-Item-SgNBPDCPnotpresent ::= SEQUENCE {
    sgNB-DL-GTP-TEIDatSCG                   GTPtunnelEndpoint                                                                                               OPTIONAL,
    iE-Extensions                   ProtocolExtensionContainer { {E-RABs-Admitted-ToBeModified-SgNBModAck-Item-SgNBPDCPnotpresentExtIEs} }  OPTIONAL,
    ...
}

E-RABs-Admitted-ToBeModified-SgNBModAck-Item-SgNBPDCPnotpresentExtIEs X2AP-PROTOCOL-EXTENSION ::= {
    { ID id-secondarysgNBDLGTPTEIDatPDCP            CRITICALITY ignore  EXTENSION GTPtunnelEndpoint             PRESENCE optional}|
    { ID id-RLC-Status                              CRITICALITY ignore          EXTENSION RLC-Status                PRESENCE optional },
    ...
}

E-RABs-Admitted-ToBeReleased-SgNBModAckList ::= SEQUENCE (SIZE (1..maxnoofBearers)) OF ProtocolIE-Single-Container { {E-RABs-Admitted-ToBeReleased-SgNBModAck-ItemIEs} }

E-RABs-Admitted-ToBeReleased-SgNBModAck-ItemIEs X2AP-PROTOCOL-IES ::= {
    { ID id-E-RABs-Admitted-ToBeReleased-SgNBModAck-Item        CRITICALITY ignore  TYPE E-RABs-Admitted-ToReleased-SgNBModAck-Item     PRESENCE mandatory}
}

E-RABs-Admitted-ToReleased-SgNBModAck-Item ::= SEQUENCE {
    e-RAB-ID                            E-RAB-ID,
    en-DC-ResourceConfiguration         EN-DC-ResourceConfiguration,
    resource-configuration              CHOICE {
        sgNBPDCPpresent                     E-RABs-Admitted-ToBeReleased-SgNBModAck-Item-SgNBPDCPpresent,
        sgNBPDCPnotpresent                  E-RABs-Admitted-ToBeReleased-SgNBModAck-Item-SgNBPDCPnotpresent,
        ...
    },
    iE-Extensions                   ProtocolExtensionContainer { {E-RABs-ToBeReleased-SgNBModAck-ItemExtIEs} }  OPTIONAL,
    ...
}

E-RABs-ToBeReleased-SgNBModAck-ItemExtIEs X2AP-PROTOCOL-EXTENSION ::= {
    ...
}

E-RABs-Admitted-ToBeReleased-SgNBModAck-Item-SgNBPDCPpresent ::= SEQUENCE {
    iE-Extensions               ProtocolExtensionContainer { {E-RABs-Admitted-ToBeReleased-SgNBModAck-Item-SgNBPDCPpresentExtIEs} }     OPTIONAL,
    ...
}

E-RABs-Admitted-ToBeReleased-SgNBModAck-Item-SgNBPDCPpresentExtIEs X2AP-PROTOCOL-EXTENSION ::= {
    ...
}

E-RABs-Admitted-ToBeReleased-SgNBModAck-Item-SgNBPDCPnotpresent ::= SEQUENCE {
    iE-Extensions               ProtocolExtensionContainer { {E-RABs-Admitted-ToBeReleased-SgNBModAck-Item-SgNBPDCPnotpresentExtIEs} } OPTIONAL,
    ...
}

E-RABs-Admitted-ToBeReleased-SgNBModAck-Item-SgNBPDCPnotpresentExtIEs X2AP-PROTOCOL-EXTENSION ::= {
    ...
}


-- **************************************************************
--
-- SGNB MODIFICATION REQUEST REJECT
--
-- **************************************************************

SgNBModificationRequestReject ::= SEQUENCE {
    protocolIEs     ProtocolIE-Container    {{SgNBModificationRequestReject-IEs}},
    ...
}

SgNBModificationRequestReject-IEs X2AP-PROTOCOL-IES ::= {
    { ID id-MeNB-UE-X2AP-ID                     CRITICALITY ignore  TYPE UE-X2AP-ID                 PRESENCE mandatory}|
    { ID id-SgNB-UE-X2AP-ID                     CRITICALITY ignore  TYPE SgNB-UE-X2AP-ID                PRESENCE mandatory}|
    { ID id-Cause                               CRITICALITY ignore  TYPE Cause                      PRESENCE mandatory}|
    { ID id-CriticalityDiagnostics              CRITICALITY ignore  TYPE CriticalityDiagnostics     PRESENCE optional}|
    { ID id-MeNB-UE-X2AP-ID-Extension           CRITICALITY ignore  TYPE UE-X2AP-ID-Extension       PRESENCE optional},
    ...
}


-- **************************************************************
--
-- SGNB MODIFICATION REQUIRED
--
-- **************************************************************

SgNBModificationRequired ::= SEQUENCE {
    protocolIEs     ProtocolIE-Container        {{SgNBModificationRequired-IEs}},
    ...
}

SgNBModificationRequired-IEs X2AP-PROTOCOL-IES ::= {
    { ID id-MeNB-UE-X2AP-ID                         CRITICALITY reject  TYPE UE-X2AP-ID                                     PRESENCE mandatory}|
    { ID id-SgNB-UE-X2AP-ID                         CRITICALITY reject  TYPE SgNB-UE-X2AP-ID                                PRESENCE mandatory}|
    { ID id-Cause                                   CRITICALITY ignore  TYPE Cause                                          PRESENCE mandatory}|
    { ID id-PDCPChangeIndication                    CRITICALITY ignore  TYPE PDCPChangeIndication                           PRESENCE optional}|
    { ID id-E-RABs-ToBeReleased-SgNBModReqdList     CRITICALITY ignore  TYPE E-RABs-ToBeReleased-SgNBModReqdList        PRESENCE optional}|
    { ID id-SgNBtoMeNBContainer                     CRITICALITY ignore  TYPE SgNBtoMeNBContainer                            PRESENCE optional}|
    { ID id-MeNB-UE-X2AP-ID-Extension               CRITICALITY reject  TYPE UE-X2AP-ID-Extension                           PRESENCE optional}|
    { ID id-E-RABs-ToBeModified-SgNBModReqdList     CRITICALITY ignore  TYPE E-RABs-ToBeModified-SgNBModReqdList        PRESENCE optional}|
    { ID id-SgNBResourceCoordinationInformation     CRITICALITY ignore  TYPE SgNBResourceCoordinationInformation        PRESENCE optional}|
    { ID id-RRCConfigIndication                     CRITICALITY reject  TYPE RRC-Config-Ind                                 PRESENCE optional}|
    { ID id-LocationInformationSgNB                 CRITICALITY ignore  TYPE LocationInformationSgNB                        PRESENCE optional}|
    { ID id-SCG-UE-HistoryInformation               CRITICALITY ignore  TYPE SCG-UE-HistoryInformation                  PRESENCE optional}|
    { ID id-SCGActivationRequest                    CRITICALITY ignore  TYPE SCGActivationRequest                           PRESENCE optional}|
    { ID id-CPACinformation-REQD                    CRITICALITY ignore  TYPE CPACinformation-REQD                           PRESENCE optional}|
    { ID id-SCGreconfigNotification                 CRITICALITY ignore  TYPE SCGreconfigNotification                        PRESENCE optional},
    ...
}


E-RABs-ToBeReleased-SgNBModReqdList ::= SEQUENCE (SIZE (1..maxnoofBearers)) OF ProtocolIE-Single-Container { {E-RABs-ToBeReleased-SgNBModReqd-ItemIEs} }

E-RABs-ToBeReleased-SgNBModReqd-ItemIEs X2AP-PROTOCOL-IES ::= {
    { ID id-E-RABs-ToBeReleased-SgNBModReqd-Item     CRITICALITY ignore     TYPE E-RABs-ToBeReleased-SgNBModReqd-Item       PRESENCE mandatory },
    ...
}

E-RABs-ToBeReleased-SgNBModReqd-Item ::= SEQUENCE {
    e-RAB-ID                            E-RAB-ID,
    cause                           Cause,
    iE-Extensions                   ProtocolExtensionContainer { {E-RABs-ToBeReleased-SgNBModReqd-ItemExtIEs} } OPTIONAL,
    ...
}

E-RABs-ToBeReleased-SgNBModReqd-ItemExtIEs X2AP-PROTOCOL-EXTENSION ::= {
    { ID id-RLCMode-transferred                 CRITICALITY ignore  EXTENSION RLCMode                   PRESENCE optional},
    ...
}

E-RABs-ToBeModified-SgNBModReqdList ::= SEQUENCE (SIZE (1..maxnoofBearers)) OF ProtocolIE-Single-Container { {E-RABs-ToBeModified-SgNBModReqd-ItemIEs} }

E-RABs-ToBeModified-SgNBModReqd-ItemIEs X2AP-PROTOCOL-IES ::= {
    { ID id-E-RABs-ToBeModified-SgNBModReqd-Item     CRITICALITY ignore     TYPE E-RABs-ToBeModified-SgNBModReqd-Item       PRESENCE mandatory },
    ...
}

E-RABs-ToBeModified-SgNBModReqd-Item ::= SEQUENCE {
    e-RAB-ID                                E-RAB-ID,
    en-DC-ResourceConfiguration         EN-DC-ResourceConfiguration,
    resource-configuration              CHOICE {
        sgNBPDCPpresent                     E-RABs-ToBeModified-SgNBModReqd-Item-SgNBPDCPpresent,
        sgNBPDCPnotpresent                  E-RABs-ToBeModified-SgNBModReqd-Item-SgNBPDCPnotpresent,
        ...
    },
    iE-Extensions                   ProtocolExtensionContainer { {E-RABs-ToBeModified-SgNBModReqd-ItemExtIEs} } OPTIONAL,
    ...
}

E-RABs-ToBeModified-SgNBModReqd-ItemExtIEs X2AP-PROTOCOL-EXTENSION ::= {
    ...
}

E-RABs-ToBeModified-SgNBModReqd-Item-SgNBPDCPpresent ::= SEQUENCE {
    requested-MCG-E-RAB-Level-QoS-Parameters        E-RAB-Level-QoS-Parameters                                                  OPTIONAL,
    uL-Configuration                                ULConfiguration                                                             OPTIONAL,
    sgNB-UL-GTP-TEIDatPDCP                      GTPtunnelEndpoint                                                           OPTIONAL,
    s1-DL-GTP-TEIDatSgNB                            GTPtunnelEndpoint                                                           OPTIONAL,
    iE-Extensions               ProtocolExtensionContainer { {E-RABs-ToBeModified-SgNBModReqd-Item-SgNBPDCPpresentExtIEs} }     OPTIONAL,
    ...
}

E-RABs-ToBeModified-SgNBModReqd-Item-SgNBPDCPpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional}|
    { ID id-new-drb-ID-req                          CRITICALITY ignore  EXTENSION NewDRBIDrequest               PRESENCE optional},
    ...
}

E-RABs-ToBeModified-SgNBModReqd-Item-SgNBPDCPnotpresent ::= SEQUENCE {
    sgNB-DL-GTP-TEIDatSCG               GTPtunnelEndpoint               OPTIONAL,
    secondary-sgNB-DL-GTP-TEIDatSCG     GTPtunnelEndpoint               OPTIONAL,
    iE-Extensions               ProtocolExtensionContainer { {E-RABs-ToBeModified-SgNBModReqd-Item-SgNBPDCPnotpresentExtIEs} }      OPTIONAL,
    ...
}

E-RABs-ToBeModified-SgNBModReqd-Item-SgNBPDCPnotpresentExtIEs X2AP-PROTOCOL-EXTENSION ::= {
    { ID id-RLC-Status          CRITICALITY ignore          EXTENSION RLC-Status                PRESENCE optional}|
    { ID id-lCID                CRITICALITY ignore          EXTENSION LCID                      PRESENCE optional},
    ...
}


-- **************************************************************
--
-- SGNB MODIFICATION CONFIRM
--
-- **************************************************************

SgNBModificationConfirm ::= SEQUENCE {
    protocolIEs     ProtocolIE-Container    {{SgNBModificationConfirm-IEs}},
    ...
}

SgNBModificationConfirm-IEs X2AP-PROTOCOL-IES ::= {
    { ID id-MeNB-UE-X2AP-ID                             CRITICALITY ignore  TYPE UE-X2AP-ID                                                 PRESENCE mandatory}|
    { ID id-SgNB-UE-X2AP-ID                             CRITICALITY ignore  TYPE SgNB-UE-X2AP-ID                                                PRESENCE mandatory}|
    { ID id-E-RABs-AdmittedToBeModified-SgNBModConfList CRITICALITY ignore  TYPE E-RABs-AdmittedToBeModified-SgNBModConfList        PRESENCE optional}|
    { ID id-MeNBtoSgNBContainer                         CRITICALITY ignore  TYPE MeNBtoSgNBContainer                                        PRESENCE optional}|
    { ID id-CriticalityDiagnostics                      CRITICALITY ignore  TYPE CriticalityDiagnostics                                 PRESENCE optional}|
    { ID id-MeNB-UE-X2AP-ID-Extension                   CRITICALITY ignore  TYPE UE-X2AP-ID-Extension                                   PRESENCE optional}|
    { ID id-MeNBResourceCoordinationInformation         CRITICALITY ignore  TYPE MeNBResourceCoordinationInformation                PRESENCE optional},
    ...
}

E-RABs-AdmittedToBeModified-SgNBModConfList ::= SEQUENCE (SIZE (1..maxnoofBearers)) OF ProtocolIE-Single-Container
    { {E-RABs-AdmittedToBeModified-SgNBModConf-ItemIEs} }

E-RABs-AdmittedToBeModified-SgNBModConf-ItemIEs X2AP-PROTOCOL-IES ::= {
{ ID id-E-RABs-AdmittedToBeModified-SgNBModConf-Item     CRITICALITY ignore TYPE E-RABs-AdmittedToBeModified-SgNBModConf-Item    PRESENCE mandatory },
    ...
}

E-RABs-AdmittedToBeModified-SgNBModConf-Item ::= SEQUENCE {
    e-RAB-ID                                E-RAB-ID,
    en-DC-ResourceConfiguration         EN-DC-ResourceConfiguration,
    resource-configuration              CHOICE {
        sgNBPDCPpresent                     E-RABs-AdmittedToBeModified-SgNBModConf-Item-SgNBPDCPpresent,
        sgNBPDCPnotpresent                  E-RABs-AdmittedToBeModified-SgNBModConf-Item-SgNBPDCPnotpresent,
        ...
    },
    iE-Extensions                   ProtocolExtensionContainer { {E-RABs-AdmittedToBeModified-SgNBModConf-ItemExtIEs} } OPTIONAL,
    ...
}

E-RABs-AdmittedToBeModified-SgNBModConf-ItemExtIEs X2AP-PROTOCOL-EXTENSION ::= {
    ...
}

E-RABs-AdmittedToBeModified-SgNBModConf-Item-SgNBPDCPpresent ::= SEQUENCE {
    iE-Extensions               ProtocolExtensionContainer { {E-RABs-AdmittedToBeModified-SgNBModConf-Item-SgNBPDCPpresentExtIEs} }     OPTIONAL,
    ...
}

E-RABs-AdmittedToBeModified-SgNBModConf-Item-SgNBPDCPpresentExtIEs X2AP-PROTOCOL-EXTENSION ::= {
    ...
}

E-RABs-AdmittedToBeModified-SgNBModConf-Item-SgNBPDCPnotpresent ::= SEQUENCE {
    secondary-meNB-UL-GTP-TEIDatPDCP                GTPtunnelEndpoint               OPTIONAL,
    iE-Extensions               ProtocolExtensionContainer { {E-RABs-AdmittedToBeModified-SgNBModConf-Item-SgNBPDCPnotpresentExtIEs} }      OPTIONAL,
    ...
}

E-RABs-AdmittedToBeModified-SgNBModConf-Item-SgNBPDCPnotpresentExtIEs X2AP-PROTOCOL-EXTENSION ::= {
    { ID id-uLpDCPSnLength                          CRITICALITY ignore  EXTENSION PDCPSnLength                  PRESENCE optional}|
    { ID id-dLPDCPSnLength                          CRITICALITY ignore  EXTENSION PDCPSnLength                  PRESENCE optional},
    ...
}

-- **************************************************************
--
-- SGNB MODIFICATION REFUSE
--
-- **************************************************************

SgNBModificationRefuse ::= SEQUENCE {
    protocolIEs     ProtocolIE-Container        {{SgNBModificationRefuse-IEs}},
    ...
}

SgNBModificationRefuse-IEs X2AP-PROTOCOL-IES ::= {
    { ID id-MeNB-UE-X2AP-ID                     CRITICALITY ignore  TYPE UE-X2AP-ID                 PRESENCE mandatory}|
    { ID id-SgNB-UE-X2AP-ID                     CRITICALITY ignore  TYPE SgNB-UE-X2AP-ID                PRESENCE mandatory}|
    { ID id-Cause                               CRITICALITY ignore  TYPE Cause                      PRESENCE mandatory}|
    { ID id-MeNBtoSgNBContainer                 CRITICALITY ignore  TYPE MeNBtoSgNBContainer            PRESENCE optional}|
    { ID id-CriticalityDiagnostics              CRITICALITY ignore  TYPE CriticalityDiagnostics     PRESENCE optional}|
    { ID id-MeNB-UE-X2AP-ID-Extension           CRITICALITY ignore  TYPE UE-X2AP-ID-Extension       PRESENCE optional},
    ...
}

-- **************************************************************
--
-- SGNB RELEASE REQUEST
--
-- **************************************************************

SgNBReleaseRequest ::= SEQUENCE {
    protocolIEs     ProtocolIE-Container        {{SgNBReleaseRequest-IEs}},
    ...
}

SgNBReleaseRequest-IEs X2AP-PROTOCOL-IES ::= {
    { ID id-MeNB-UE-X2AP-ID                         CRITICALITY reject  TYPE UE-X2AP-ID                                     PRESENCE mandatory}|
    { ID id-SgNB-UE-X2AP-ID                         CRITICALITY reject  TYPE SgNB-UE-X2AP-ID                                    PRESENCE optional}|
    { ID id-Cause                                   CRITICALITY ignore  TYPE Cause                                          PRESENCE mandatory}|
    { ID id-E-RABs-ToBeReleased-SgNBRelReqList      CRITICALITY ignore  TYPE E-RABs-ToBeReleased-SgNBRelReqList     PRESENCE optional}|
    { ID id-UE-ContextKeptIndicator                 CRITICALITY ignore  TYPE UE-ContextKeptIndicator                        PRESENCE optional}|
    { ID id-MeNB-UE-X2AP-ID-Extension               CRITICALITY reject  TYPE UE-X2AP-ID-Extension                           PRESENCE optional}|
    { ID id-MeNBtoSgNBContainer                     CRITICALITY reject  TYPE MeNBtoSgNBContainer                                PRESENCE optional}|
    { ID id-ERABs-transferred-to-MeNB               CRITICALITY ignore  TYPE E-RAB-List                                     PRESENCE optional},
    ...
}

E-RABs-ToBeReleased-SgNBRelReqList ::= SEQUENCE (SIZE(1..maxnoofBearers)) OF ProtocolIE-Single-Container { {E-RABs-ToBeReleased-SgNBRelReq-ItemIEs} }

E-RABs-ToBeReleased-SgNBRelReq-ItemIEs X2AP-PROTOCOL-IES ::= {
    { ID id-E-RABs-ToBeReleased-SgNBRelReq-Item     CRITICALITY ignore  TYPE E-RABs-ToBeReleased-SgNBRelReq-Item        PRESENCE mandatory},
    ...
}

E-RABs-ToBeReleased-SgNBRelReq-Item ::= SEQUENCE {
    e-RAB-ID                            E-RAB-ID,
    en-DC-ResourceConfiguration         EN-DC-ResourceConfiguration,
    resource-configuration              CHOICE {
        sgNBPDCPpresent                     E-RABs-ToBeReleased-SgNBRelReq-Item-SgNBPDCPpresent,
        sgNBPDCPnotpresent                  E-RABs-ToBeReleased-SgNBRelReq-Item-SgNBPDCPnotpresent,
        ...
    },
    iE-Extensions                   ProtocolExtensionContainer { {E-RABs-ToBeReleased-SgNBRelReq-ItemExtIEs} }  OPTIONAL,
    ...
}

E-RABs-ToBeReleased-SgNBRelReq-ItemExtIEs X2AP-PROTOCOL-EXTENSION ::= {
    ...
}


E-RABs-ToBeReleased-SgNBRelReq-Item-SgNBPDCPpresent ::= SEQUENCE {
    uL-GTPtunnelEndpoint            GTPtunnelEndpoint                                                                   OPTIONAL,
    dL-GTPtunnelEndpoint            GTPtunnelEndpoint                                                                               OPTIONAL,
    iE-Extensions                   ProtocolExtensionContainer { {E-RABs-ToBeReleased-SgNBRelReq-Item-SgNBPDCPpresentExtIEs} }  OPTIONAL,
    ...
}

E-RABs-ToBeReleased-SgNBRelReq-Item-SgNBPDCPpresentExtIEs X2AP-PROTOCOL-EXTENSION ::= {
    ...
}

E-RABs-ToBeReleased-SgNBRelReq-Item-SgNBPDCPnotpresent ::= SEQUENCE {
    iE-Extensions                   ProtocolExtensionContainer { {E-RABs-ToBeReleased-SgNBRelReq-Item-SgNBPDCPnotpresentExtIEs} }   OPTIONAL,
    ...
}

E-RABs-ToBeReleased-SgNBRelReq-Item-SgNBPDCPnotpresentExtIEs X2AP-PROTOCOL-EXTENSION ::= {
    ...
}

-- **************************************************************
--
-- SGNB RELEASE REQUEST ACKNOWLEDGE
--
-- **************************************************************

SgNBReleaseRequestAcknowledge ::= SEQUENCE {
    protocolIEs     ProtocolIE-Container        {{SgNBReleaseRequestAcknowledge-IEs}},
    ...
}

SgNBReleaseRequestAcknowledge-IEs X2AP-PROTOCOL-IES ::= {
    { ID id-MeNB-UE-X2AP-ID                                 CRITICALITY ignore  TYPE UE-X2AP-ID                                         PRESENCE mandatory}|
    { ID id-SgNB-UE-X2AP-ID                                 CRITICALITY ignore  TYPE SgNB-UE-X2AP-ID                                    PRESENCE mandatory}|
    { ID id-CriticalityDiagnostics                          CRITICALITY ignore  TYPE CriticalityDiagnostics                     PRESENCE optional }|
    { ID id-MeNB-UE-X2AP-ID-Extension                       CRITICALITY reject  TYPE UE-X2AP-ID-Extension                           PRESENCE optional }|
    { ID id-E-RABs-Admitted-ToBeReleased-SgNBRelReqAckList  CRITICALITY ignore  TYPE E-RABs-Admitted-ToBeReleased-SgNBRelReqAckList PRESENCE optional }|
    { ID id-SCG-UE-HistoryInformation                   CRITICALITY ignore  TYPE SCG-UE-HistoryInformation                          PRESENCE optional},
    ...
}

E-RABs-Admitted-ToBeReleased-SgNBRelReqAckList ::= SEQUENCE (SIZE(1..maxnoofBearers)) OF
                                        ProtocolIE-Single-Container { {E-RABs-Admitted-ToBeReleased-SgNBRelReqAck-ItemIEs} }

E-RABs-Admitted-ToBeReleased-SgNBRelReqAck-ItemIEs X2AP-PROTOCOL-IES ::= {
    { ID id-E-RABs-Admitted-ToBeReleased-SgNBRelReqAck-Item CRITICALITY ignore  TYPE E-RABs-Admitted-ToBeReleased-SgNBRelReqAck-Item        PRESENCE mandatory},
    ...
}

E-RABs-Admitted-ToBeReleased-SgNBRelReqAck-Item ::= SEQUENCE {
    e-RAB-ID                            E-RAB-ID,
    rlc-Mode-transferred            RLCMode,
    iE-Extensions                   ProtocolExtensionContainer { {E-RABs-Admitted-ToBeReleased-SgNBRelReqAck-ItemExtIEs} }  OPTIONAL,
    ...
}

E-RABs-Admitted-ToBeReleased-SgNBRelReqAck-ItemExtIEs X2AP-PROTOCOL-EXTENSION ::= {
    ...
}

-- **************************************************************
--
-- SGNB RELEASE REQUEST REJECT
--
-- **************************************************************

SgNBReleaseRequestReject ::= SEQUENCE {
    protocolIEs     ProtocolIE-Container        {{SgNBReleaseRequestReject-IEs}},
    ...
}

SgNBReleaseRequestReject-IEs X2AP-PROTOCOL-IES ::= {
    { ID id-MeNB-UE-X2AP-ID                         CRITICALITY ignore  TYPE UE-X2AP-ID                                     PRESENCE mandatory}|
    { ID id-SgNB-UE-X2AP-ID                         CRITICALITY ignore  TYPE SgNB-UE-X2AP-ID                                    PRESENCE mandatory}|
    { ID id-Cause                                   CRITICALITY ignore  TYPE Cause                                          PRESENCE mandatory}|
    { ID id-CriticalityDiagnostics                  CRITICALITY ignore  TYPE CriticalityDiagnostics                     PRESENCE optional}|
    { ID id-MeNB-UE-X2AP-ID-Extension               CRITICALITY reject  TYPE UE-X2AP-ID-Extension                           PRESENCE optional},
    ...
}

-- **************************************************************
--
-- SGNB RELEASE REQUIRED
--
-- **************************************************************

SgNBReleaseRequired ::= SEQUENCE {
    protocolIEs     ProtocolIE-Container    {{SgNBReleaseRequired-IEs}},
    ...
}

SgNBReleaseRequired-IEs X2AP-PROTOCOL-IES ::= {
    { ID id-MeNB-UE-X2AP-ID                         CRITICALITY reject  TYPE UE-X2AP-ID                                         PRESENCE mandatory}|
    { ID id-SgNB-UE-X2AP-ID                         CRITICALITY reject  TYPE SgNB-UE-X2AP-ID                                        PRESENCE mandatory}|
    { ID id-Cause                                   CRITICALITY ignore  TYPE Cause                                              PRESENCE mandatory}|
    { ID id-MeNB-UE-X2AP-ID-Extension               CRITICALITY reject  TYPE UE-X2AP-ID-Extension                               PRESENCE optional }|
    { ID id-E-RABs-ToBeReleased-SgNBRelReqdList     CRITICALITY ignore  TYPE E-RABs-ToBeReleased-SgNBRelReqdList            PRESENCE optional }|
    { ID id-SgNBtoMeNBContainer                     CRITICALITY ignore  TYPE SgNBtoMeNBContainer                                    PRESENCE optional }|
    { ID id-SCG-UE-HistoryInformation                   CRITICALITY ignore  TYPE SCG-UE-HistoryInformation                          PRESENCE optional},
    ...
}

E-RABs-ToBeReleased-SgNBRelReqdList ::= SEQUENCE (SIZE(1..maxnoofBearers)) OF ProtocolIE-Single-Container { {E-RABs-ToBeReleased-SgNBRelReqd-ItemIEs} }

E-RABs-ToBeReleased-SgNBRelReqd-ItemIEs X2AP-PROTOCOL-IES ::= {
    { ID id-E-RABs-ToBeReleased-SgNBRelReqd-Item        CRITICALITY ignore  TYPE E-RABs-ToBeReleased-SgNBRelReqd-Item       PRESENCE mandatory},
    ...
}

E-RABs-ToBeReleased-SgNBRelReqd-Item ::= SEQUENCE {
    e-RAB-ID                            E-RAB-ID,
    rlc-Mode-transferred            RLCMode,
    iE-Extensions                   ProtocolExtensionContainer { {E-RABs-ToBeReleased-SgNBRelReqd-ItemExtIEs} } OPTIONAL,
    ...
}

E-RABs-ToBeReleased-SgNBRelReqd-ItemExtIEs X2AP-PROTOCOL-EXTENSION ::= {
    ...
}

-- **************************************************************
--
-- SGNB RELEASE CONFIRM
--
-- **************************************************************

SgNBReleaseConfirm ::= SEQUENCE {
    protocolIEs     ProtocolIE-Container    {{SgNBReleaseConfirm-IEs}},
    ...
}

SgNBReleaseConfirm-IEs X2AP-PROTOCOL-IES ::= {
    { ID id-MeNB-UE-X2AP-ID                         CRITICALITY ignore  TYPE UE-X2AP-ID                                     PRESENCE mandatory}|
    { ID id-SgNB-UE-X2AP-ID                         CRITICALITY ignore  TYPE SgNB-UE-X2AP-ID                                    PRESENCE mandatory}|
    { ID id-E-RABs-ToBeReleased-SgNBRelConfList     CRITICALITY ignore  TYPE E-RABs-ToBeReleased-SgNBRelConfList        PRESENCE optional}|
    { ID id-CriticalityDiagnostics                  CRITICALITY ignore  TYPE CriticalityDiagnostics                     PRESENCE optional}|
    { ID id-MeNB-UE-X2AP-ID-Extension               CRITICALITY ignore  TYPE UE-X2AP-ID-Extension                           PRESENCE optional},
    ...
}

E-RABs-ToBeReleased-SgNBRelConfList ::= SEQUENCE (SIZE(1..maxnoofBearers)) OF ProtocolIE-Single-Container { {E-RABs-ToBeReleased-SgNBRelConf-ItemIEs} }

E-RABs-ToBeReleased-SgNBRelConf-ItemIEs X2AP-PROTOCOL-IES ::= {
    { ID id-E-RABs-ToBeReleased-SgNBRelConf-Item        CRITICALITY ignore      TYPE E-RABs-ToBeReleased-SgNBRelConf-Item       PRESENCE mandatory},
    ...
}

E-RABs-ToBeReleased-SgNBRelConf-Item ::= SEQUENCE {
    e-RAB-ID                            E-RAB-ID,
    en-DC-ResourceConfiguration         EN-DC-ResourceConfiguration,
    resource-configuration              CHOICE {
        sgNBPDCPpresent                     E-RABs-ToBeReleased-SgNBRelConf-Item-SgNBPDCPpresent,
        sgNBPDCPnotpresent                  E-RABs-ToBeReleased-SgNBRelConf-Item-SgNBPDCPnotpresent,
        ...
    },
    iE-Extensions                   ProtocolExtensionContainer { {E-RABs-ToBeReleased-SgNBRelConf-ItemExtIEs} } OPTIONAL,
    ...
}

E-RABs-ToBeReleased-SgNBRelConf-ItemExtIEs X2AP-PROTOCOL-EXTENSION ::= {
    ...
}

E-RABs-ToBeReleased-SgNBRelConf-Item-SgNBPDCPpresent ::= SEQUENCE {
    uL-GTPtunnelEndpoint            GTPtunnelEndpoint                                                                               OPTIONAL,
    dL-GTPtunnelEndpoint            GTPtunnelEndpoint                                                                               OPTIONAL,
    iE-Extensions                   ProtocolExtensionContainer { {E-RABs-ToBeReleased-SgNBRelConf-Item-SgNBPDCPpresentExtIEs} } OPTIONAL,
    ...
}

E-RABs-ToBeReleased-SgNBRelConf-Item-SgNBPDCPpresentExtIEs X2AP-PROTOCOL-EXTENSION ::= {
    ...
}

E-RABs-ToBeReleased-SgNBRelConf-Item-SgNBPDCPnotpresent ::= SEQUENCE {
    iE-Extensions                   ProtocolExtensionContainer { {E-RABs-ToBeReleased-SgNBRelConf-Item-SgNBPDCPnotpresentExtIEs} }  OPTIONAL,
    ...
}

E-RABs-ToBeReleased-SgNBRelConf-Item-SgNBPDCPnotpresentExtIEs X2AP-PROTOCOL-EXTENSION ::= {
    ...
}


-- **************************************************************
--
-- SGNB COUNTER CHECK REQUEST
--
-- **************************************************************

SgNBCounterCheckRequest ::= SEQUENCE {
    protocolIEs     ProtocolIE-Container    {{SgNBCounterCheckRequest-IEs}},
    ...
}

SgNBCounterCheckRequest-IEs X2AP-PROTOCOL-IES ::= {
    { ID id-MeNB-UE-X2AP-ID                             CRITICALITY reject  TYPE UE-X2AP-ID                                         PRESENCE mandatory}|
    { ID id-SgNB-UE-X2AP-ID                             CRITICALITY reject  TYPE SgNB-UE-X2AP-ID                                        PRESENCE mandatory}|
    { ID id-E-RABs-SubjectToSgNBCounterCheck-List       CRITICALITY ignore  TYPE E-RABs-SubjectToSgNBCounterCheck-List      PRESENCE mandatory}|
    { ID id-MeNB-UE-X2AP-ID-Extension                   CRITICALITY ignore  TYPE UE-X2AP-ID-Extension                           PRESENCE optional},
    ...
}
E-RABs-SubjectToSgNBCounterCheck-List ::= SEQUENCE (SIZE(1..maxnoofBearers)) OF ProtocolIE-Single-Container { {E-RABs-SubjectToSgNBCounterCheck-ItemIEs} }

E-RABs-SubjectToSgNBCounterCheck-ItemIEs X2AP-PROTOCOL-IES ::= {
    { ID id-E-RABs-SubjectToSgNBCounterCheck-Item       CRITICALITY ignore  TYPE E-RABs-SubjectToSgNBCounterCheck-Item      PRESENCE mandatory},
    ...
}

E-RABs-SubjectToSgNBCounterCheck-Item ::= SEQUENCE {
    e-RAB-ID                        E-RAB-ID,
    uL-Count                        INTEGER (0..4294967295),
    dL-Count                        INTEGER (0..4294967295),
    iE-Extensions                   ProtocolExtensionContainer { {E-RABs-SubjectToSgNBCounterCheck-ItemExtIEs} } OPTIONAL,
    ...
}

E-RABs-SubjectToSgNBCounterCheck-ItemExtIEs X2AP-PROTOCOL-EXTENSION ::= {
    ...
}

-- **************************************************************
--
-- SGNB CHANGE REQUIRED
--
-- **************************************************************

SgNBChangeRequired ::= SEQUENCE {
    protocolIEs     ProtocolIE-Container        {{SgNBChangeRequired-IEs}},
    ...
}

SgNBChangeRequired-IEs X2AP-PROTOCOL-IES ::= {
    { ID id-MeNB-UE-X2AP-ID                     CRITICALITY reject  TYPE UE-X2AP-ID                     PRESENCE mandatory}|
    { ID id-SgNB-UE-X2AP-ID                     CRITICALITY reject  TYPE SgNB-UE-X2AP-ID                    PRESENCE mandatory}|
    { ID id-Target-SgNB-ID                      CRITICALITY reject  TYPE GlobalGNB-ID                   PRESENCE mandatory}|
    { ID id-Cause                               CRITICALITY ignore  TYPE Cause                          PRESENCE mandatory}|
    { ID id-SgNBtoMeNBContainer                 CRITICALITY reject  TYPE SgNBtoMeNBContainer                PRESENCE optional}|
    { ID id-MeNB-UE-X2AP-ID-Extension           CRITICALITY reject  TYPE UE-X2AP-ID-Extension           PRESENCE optional}|
    { ID id-SCG-UE-HistoryInformation           CRITICALITY ignore  TYPE SCG-UE-HistoryInformation  PRESENCE optional}|
    { ID id-CPCinformation-REQD                 CRITICALITY reject  TYPE CPCinformation-REQD            PRESENCE optional},
    ...
}


-- **************************************************************
--
-- ACCESS AND MOBILITY INDICATION
--
-- **************************************************************

AccessAndMobilityIndication ::= SEQUENCE {
    protocolIEs         ProtocolIE-Container    {{ AccessAndMobilityIndication-IEs}},
    ...
}
AccessAndMobilityIndication-IEs X2AP-PROTOCOL-IES ::= {
    { ID id-NRRAReport          CRITICALITY ignore      TYPE NRRAReport         PRESENCE optional},
    ...
}

-- **************************************************************
--
-- SGNB CHANGE CONFIRM
--
-- **************************************************************

SgNBChangeConfirm ::= SEQUENCE {
    protocolIEs     ProtocolIE-Container    {{SgNBChangeConfirm-IEs}},
    ...
}

SgNBChangeConfirm-IEs X2AP-PROTOCOL-IES ::= {
    { ID id-MeNB-UE-X2AP-ID                         CRITICALITY ignore  TYPE UE-X2AP-ID                                     PRESENCE mandatory}|
    { ID id-SgNB-UE-X2AP-ID                         CRITICALITY ignore  TYPE SgNB-UE-X2AP-ID                                    PRESENCE mandatory}|
    { ID id-E-RABs-ToBeReleased-SgNBChaConfList     CRITICALITY ignore  TYPE E-RABs-ToBeReleased-SgNBChaConfList        PRESENCE optional}|
    { ID id-CriticalityDiagnostics                  CRITICALITY ignore  TYPE CriticalityDiagnostics                     PRESENCE optional}|
    { ID id-MeNB-UE-X2AP-ID-Extension               CRITICALITY ignore  TYPE UE-X2AP-ID-Extension                       PRESENCE optional}|
    { ID id-CPCinformation-CONF                     CRITICALITY ignore  TYPE CPCinformation-CONF                            PRESENCE optional}|
    { ID id-MeNBtoSgNBContainer                     CRITICALITY ignore  TYPE MeNBtoSgNBContainer                            PRESENCE optional},
    ...
}

E-RABs-ToBeReleased-SgNBChaConfList ::= SEQUENCE (SIZE(1..maxnoofBearers)) OF ProtocolIE-Single-Container { {E-RABs-ToBeReleased-SgNBChaConf-ItemIEs} }

E-RABs-ToBeReleased-SgNBChaConf-ItemIEs X2AP-PROTOCOL-IES ::= {
    { ID id-E-RABs-ToBeReleased-SgNBChaConf-Item        CRITICALITY ignore      TYPE E-RABs-ToBeReleased-SgNBChaConf-Item       PRESENCE mandatory},
    ...
}

E-RABs-ToBeReleased-SgNBChaConf-Item ::= SEQUENCE {
    e-RAB-ID                            E-RAB-ID,
    en-DC-ResourceConfiguration         EN-DC-ResourceConfiguration,
    resource-configuration              CHOICE {
        sgNBPDCPpresent                     E-RABs-ToBeReleased-SgNBChaConf-Item-SgNBPDCPpresent,
        sgNBPDCPnotpresent                  E-RABs-ToBeReleased-SgNBChaConf-Item-SgNBPDCPnotpresent,
        ...
    },
    iE-Extensions                   ProtocolExtensionContainer { {E-RABs-ToBeReleased-SgNBChaConf-ItemExtIEs} } OPTIONAL,
    ...
}

E-RABs-ToBeReleased-SgNBChaConf-ItemExtIEs X2AP-PROTOCOL-EXTENSION ::= {
    ...
}

E-RABs-ToBeReleased-SgNBChaConf-Item-SgNBPDCPpresent ::= SEQUENCE {
    uL-GTPtunnelEndpoint            GTPtunnelEndpoint                                                                               OPTIONAL,
    dL-GTPtunnelEndpoint            GTPtunnelEndpoint                                                                               OPTIONAL,
    iE-Extensions                   ProtocolExtensionContainer { {E-RABs-ToBeReleased-SgNBChaConf-Item-SgNBPDCPpresentExtIEs} } OPTIONAL,
    ...
}

E-RABs-ToBeReleased-SgNBChaConf-Item-SgNBPDCPpresentExtIEs X2AP-PROTOCOL-EXTENSION ::= {
    { ID id-AdditionalListofForwardingGTPTunnelEndpoint             CRITICALITY ignore  EXTENSION AdditionalListofForwardingGTPTunnelEndpoint                       PRESENCE optional },
    ...
}

E-RABs-ToBeReleased-SgNBChaConf-Item-SgNBPDCPnotpresent ::= SEQUENCE {
    iE-Extensions                   ProtocolExtensionContainer { {E-RABs-ToBeReleased-SgNBChaConf-Item-SgNBPDCPnotpresentExtIEs} }  OPTIONAL,
    ...
}

E-RABs-ToBeReleased-SgNBChaConf-Item-SgNBPDCPnotpresentExtIEs X2AP-PROTOCOL-EXTENSION ::= {
    ...
}

-- **************************************************************
--
-- RRC TRANSFER
--
-- **************************************************************

RRCTransfer ::= SEQUENCE {
    protocolIEs     ProtocolIE-Container        {{RRCTransfer-IEs}},
    ...
}

RRCTransfer-IEs X2AP-PROTOCOL-IES ::= {
    { ID id-MeNB-UE-X2AP-ID                     CRITICALITY reject  TYPE UE-X2AP-ID                 PRESENCE mandatory}|
    { ID id-SgNB-UE-X2AP-ID                     CRITICALITY reject  TYPE SgNB-UE-X2AP-ID                PRESENCE mandatory}|
    { ID id-SplitSRB                                CRITICALITY reject  TYPE SplitSRB                   PRESENCE optional}|
    { ID id-NRUeReport                          CRITICALITY reject  TYPE NRUeReport                 PRESENCE optional}|
    { ID id-MeNB-UE-X2AP-ID-Extension           CRITICALITY reject  TYPE UE-X2AP-ID-Extension       PRESENCE optional}|
    { ID id-FastMCGRecovery-SN-to-MN                CRITICALITY ignore  TYPE FastMCGRecovery                PRESENCE optional}|
    { ID id-FastMCGRecovery-MN-to-SN                CRITICALITY ignore  TYPE FastMCGRecovery                PRESENCE optional},
    ...
}

-- **************************************************************
--
-- SGNB CHANGE REFUSE
--
-- **************************************************************

SgNBChangeRefuse ::= SEQUENCE {
    protocolIEs     ProtocolIE-Container        {{SgNBChangeRefuse-IEs}},
    ...
}

SgNBChangeRefuse-IEs X2AP-PROTOCOL-IES ::= {
    { ID id-MeNB-UE-X2AP-ID                     CRITICALITY ignore  TYPE UE-X2AP-ID                 PRESENCE mandatory}|
    { ID id-SgNB-UE-X2AP-ID                     CRITICALITY ignore  TYPE SgNB-UE-X2AP-ID                PRESENCE mandatory}|
    { ID id-Cause                               CRITICALITY ignore  TYPE Cause                      PRESENCE mandatory}|
    { ID id-CriticalityDiagnostics              CRITICALITY ignore  TYPE CriticalityDiagnostics     PRESENCE optional}|
    { ID id-MeNB-UE-X2AP-ID-Extension           CRITICALITY reject  TYPE UE-X2AP-ID-Extension       PRESENCE optional},
    ...
}

-- **************************************************************
--
-- EN-DC X2 SETUP REQUEST
--
-- **************************************************************

ENDCX2SetupRequest ::= SEQUENCE {
    protocolIEs     ProtocolIE-Container    {{ENDCX2SetupRequest-IEs}},
    ...
}

ENDCX2SetupRequest-IEs X2AP-PROTOCOL-IES ::= {
    { ID id-InitiatingNodeType-EndcX2Setup          CRITICALITY reject  TYPE InitiatingNodeType-EndcX2Setup     PRESENCE mandatory}|
    { ID id-InterfaceInstanceIndication             CRITICALITY reject  TYPE InterfaceInstanceIndication            PRESENCE optional}|
    { ID id-TNLConfigurationInfo                    CRITICALITY ignore  TYPE TNLConfigurationInfo                       PRESENCE optional},
    ...
}

InitiatingNodeType-EndcX2Setup ::= CHOICE {
    init-eNB                ProtocolIE-Container    {{ENB-ENDCX2SetupReqIEs}},
    init-en-gNB         ProtocolIE-Container    {{En-gNB-ENDCX2SetupReqIEs}},
    ...
}

ENB-ENDCX2SetupReqIEs X2AP-PROTOCOL-IES ::= {
    { ID id-GlobalENB-ID                                CRITICALITY reject  TYPE GlobalENB-ID                                       PRESENCE mandatory}|
    { ID id-ServedEUTRAcellsENDCX2ManagementList        CRITICALITY reject  TYPE ServedEUTRAcellsENDCX2ManagementList       PRESENCE mandatory}|
    { ID id-InterfaceInstanceIndication             CRITICALITY reject  TYPE InterfaceInstanceIndication                    PRESENCE optional }|
-- NOTE: In the current version of this specification the Interface Instance Indication IE is not included in the Initiating NodeType IE --
    { ID id-CellandCapacityAssistInfo               CRITICALITY ignore  TYPE CellandCapacityAssistInfo                      PRESENCE optional },
    ...
}

ServedEUTRAcellsENDCX2ManagementList ::= SEQUENCE (SIZE (1.. maxCellineNB)) OF SEQUENCE {
    servedEUTRACellInfo                 ServedCell-Information,
    nrNeighbourInfo                     NRNeighbour-Information     OPTIONAL,
    iE-Extensions                       ProtocolExtensionContainer { {ServedEUTRAcellsENDCX2Management-ExtIEs} } OPTIONAL,
    ...
}

ServedEUTRAcellsENDCX2Management-ExtIEs X2AP-PROTOCOL-EXTENSION ::= {
    ...
}

En-gNB-ENDCX2SetupReqIEs X2AP-PROTOCOL-IES ::= {
    { ID id-Globalen-gNB-ID                         CRITICALITY reject  TYPE GlobalGNB-ID                                       PRESENCE mandatory}|
    { ID id-ServedNRcellsENDCX2ManagementList       CRITICALITY reject  TYPE ServedNRcellsENDCX2ManagementList          PRESENCE mandatory}|
    { ID id-PartialListIndicator                        CRITICALITY ignore  TYPE PartialListIndicator                               PRESENCE optional },
    ...
}

ServedNRcellsENDCX2ManagementList ::= SEQUENCE (SIZE (1.. maxCellinengNB)) OF SEQUENCE {
    servedNRCellInfo                        ServedNRCell-Information,
    nRNeighbourInfo                     NRNeighbour-Information OPTIONAL,
    iE-Extensions                       ProtocolExtensionContainer { {En-gNBServedCells-ExtIEs} } OPTIONAL,
    ...
}

En-gNBServedCells-ExtIEs X2AP-PROTOCOL-EXTENSION ::= {
    { ID id-ServedCellSpecificInfoReq-NR    CRITICALITY ignore EXTENSION ServedCellSpecificInfoReq-NR   PRESENCE optional },
    ...
}

ServedNRCell-Information ::= SEQUENCE {
    nrpCI               NRPCI,
    nrCellID            NRCGI,
    fiveGS-TAC          FiveGS-TAC  OPTIONAL,
    configured-TAC      TAC         OPTIONAL,
    broadcastPLMNs      BroadcastPLMNs-Item,
    nrModeInfo          CHOICE {
        fdd     FDD-InfoServedNRCell-Information,
        tdd     TDD-InfoServedNRCell-Information,
        ...
    },
    measurementTimingConfiguration  OCTET STRING,
    iE-Extensions                       ProtocolExtensionContainer { {ServedNRCell-Information-ExtIEs} } OPTIONAL,
    ...
}

ServedNRCell-Information-ExtIEs X2AP-PROTOCOL-EXTENSION ::= {
    { ID id-additionalPLMNs-Item            CRITICALITY ignore  EXTENSION AdditionalPLMNs-Item                  PRESENCE optional}|
    { ID id-BPLMN-ID-Info-NR                CRITICALITY ignore  EXTENSION BPLMN-ID-Info-NR                      PRESENCE optional}|
    { ID id-SSB-PositionsInBurst            CRITICALITY ignore  EXTENSION SSB-PositionsInBurst                  PRESENCE optional}|
    { ID id-NRCellPRACHConfig               CRITICALITY ignore  EXTENSION NRCellPRACHConfig                     PRESENCE optional}|
    { ID id-CSI-RSTransmissionIndication    CRITICALITY ignore  EXTENSION CSI-RSTransmissionIndication      PRESENCE optional}|
    { ID id-SFN-Offset                      CRITICALITY ignore EXTENSION SFN-Offset                             PRESENCE optional}|
    { ID id-Additional-Measurement-Timing-Configuration-List        CRITICALITY ignore  EXTENSION Additional-Measurement-Timing-Configuration-List      PRESENCE optional },
    ...
}

FDD-InfoServedNRCell-Information ::= SEQUENCE {
    ul-NRFreqInfo               NRFreqInfo,
    dl-NRFreqInfo               NRFreqInfo,
    ul-NR-TxBW              NR-TxBW,
    dl-NR-TxBW              NR-TxBW,
    iE-Extensions           ProtocolExtensionContainer { {FDD-InfoServedNRCell-Information-ExtIEs} }        OPTIONAL,
    ...
}

FDD-InfoServedNRCell-Information-ExtIEs X2AP-PROTOCOL-EXTENSION ::= {
    { ID id-ULCarrierList                   CRITICALITY ignore  EXTENSION NRCarrierList         PRESENCE optional }|
    { ID id-DLCarrierList                   CRITICALITY ignore  EXTENSION NRCarrierList         PRESENCE optional },
    ...
}

TDD-InfoServedNRCell-Information ::= SEQUENCE {
    nRFreqInfo              NRFreqInfo,
    nR-TxBW                 NR-TxBW,
    iE-Extensions           ProtocolExtensionContainer { {TDD-InfoServedNRCell-Information-ExtIEs} }        OPTIONAL,
    ...
}

TDD-InfoServedNRCell-Information-ExtIEs X2AP-PROTOCOL-EXTENSION ::= {
    { ID id-TDDULDLConfigurationCommonNR    CRITICALITY ignore  EXTENSION TDDULDLConfigurationCommonNR  PRESENCE optional}|
    { ID id-CarrierList                     CRITICALITY ignore  EXTENSION NRCarrierList         PRESENCE optional}|
    { ID id-IntendedTDD-DL-ULConfiguration-NR   CRITICALITY ignore  EXTENSION IntendedTDD-DL-ULConfiguration-NR     PRESENCE optional},
    ...
}

CellandCapacityAssistInfo::= SEQUENCE {
    maximumCellListSize                             MaximumCellListSize         OPTIONAL,
    cellAssistanceInformation                       CellAssistanceInformation   OPTIONAL,
    iE-Extensions                                   ProtocolExtensionContainer { {CellandCapacityAssistInfo-ExtIEs} } OPTIONAL,
    ...
}

CellandCapacityAssistInfo-ExtIEs X2AP-PROTOCOL-EXTENSION ::= {
    ...
}

CellAssistanceInformation ::= CHOICE {
    limited-list                Limited-list,
    full-list               ENUMERATED {allServedNRcells, ...},
    ...
}


Limited-list    ::= SEQUENCE (SIZE (1..maxCellinengNB)) OF SEQUENCE {
    nrCellID            NRCGI,
        iE-Extensions                       ProtocolExtensionContainer { {Limited-list-ExtIEs} } OPTIONAL,
    ...
}

Limited-list-ExtIEs X2AP-PROTOCOL-EXTENSION ::= {
    ...
}

-- **************************************************************
--
-- EN-DC X2 SETUP RESPONSE
--
-- **************************************************************

ENDCX2SetupResponse ::= SEQUENCE {
    protocolIEs     ProtocolIE-Container    {{ENDCX2SetupResponse-IEs}},
    ...
}

ENDCX2SetupResponse-IEs X2AP-PROTOCOL-IES ::= {
    { ID id-RespondingNodeType-EndcX2Setup      CRITICALITY reject  TYPE RespondingNodeType-EndcX2Setup     PRESENCE mandatory}|
    { ID id-InterfaceInstanceIndication         CRITICALITY reject  TYPE InterfaceInstanceIndication            PRESENCE optional }|
    { ID id-TNLConfigurationInfo                    CRITICALITY ignore  TYPE TNLConfigurationInfo                   PRESENCE optional },
    ...
}

RespondingNodeType-EndcX2Setup ::= CHOICE {
    respond-eNB         ProtocolIE-Container    {{ENB-ENDCX2SetupReqAckIEs}},
    respond-en-gNB      ProtocolIE-Container    {{En-gNB-ENDCX2SetupReqAckIEs}},
    ...
}

ENB-ENDCX2SetupReqAckIEs X2AP-PROTOCOL-IES ::= {
    { ID id-GlobalENB-ID                                CRITICALITY reject  TYPE GlobalENB-ID                                       PRESENCE mandatory}|
    { ID id-ServedEUTRAcellsENDCX2ManagementList        CRITICALITY reject  TYPE ServedEUTRAcellsENDCX2ManagementList       PRESENCE mandatory}|
    { ID id-InterfaceInstanceIndication             CRITICALITY reject  TYPE InterfaceInstanceIndication                    PRESENCE optional }|
-- NOTE: In the current version of this specification the Interface Instance Indication IE is not included in the Responding NodeType IE --
    { ID id-CellandCapacityAssistInfo               CRITICALITY ignore  TYPE CellandCapacityAssistInfo                      PRESENCE optional },
    ...
}


En-gNB-ENDCX2SetupReqAckIEs X2AP-PROTOCOL-IES ::= {
    { ID id-Globalen-gNB-ID                         CRITICALITY reject  TYPE GlobalGNB-ID                                       PRESENCE mandatory}|
    { ID id-ServedNRcellsENDCX2ManagementList       CRITICALITY reject  TYPE ServedNRcellsENDCX2ManagementList          PRESENCE mandatory}|
    { ID id-PartialListIndicator                        CRITICALITY ignore  TYPE PartialListIndicator                               PRESENCE optional },
    ...
}

-- **************************************************************
--
-- EN-DC X2 SETUP FAILURE
--
-- **************************************************************

ENDCX2SetupFailure ::= SEQUENCE {
    protocolIEs     ProtocolIE-Container    {{ENDCX2SetupFailure-IEs}},
    ...
}

ENDCX2SetupFailure-IEs X2AP-PROTOCOL-IES ::= {
    { ID id-Cause                           CRITICALITY ignore      TYPE Cause                              PRESENCE mandatory} |
    { ID id-CriticalityDiagnostics          CRITICALITY ignore      TYPE CriticalityDiagnostics             PRESENCE optional } |
    { ID id-TimeToWait                      CRITICALITY ignore      TYPE TimeToWait                         PRESENCE optional   } |
    { ID id-InterfaceInstanceIndication     CRITICALITY reject      TYPE InterfaceInstanceIndication        PRESENCE optional }|
    { ID id-MessageOversizeNotification     CRITICALITY ignore      TYPE MessageOversizeNotification        PRESENCE optional },
    ...
}

-- **************************************************************
--
-- EN-DC CONFIGURATION UPDATE
--
-- **************************************************************

ENDCConfigurationUpdate ::= SEQUENCE {
    protocolIEs     ProtocolIE-Container    {{ENDCConfigurationUpdate-IEs}},
    ...
}

ENDCConfigurationUpdate-IEs X2AP-PROTOCOL-IES ::= {
    { ID id-InitiatingNodeType-EndcConfigUpdate         CRITICALITY reject  TYPE InitiatingNodeType-EndcConfigUpdate            PRESENCE mandatory}|
    { ID id-InterfaceInstanceIndication                 CRITICALITY reject  TYPE InterfaceInstanceIndication                        PRESENCE optional}|
    { ID id-TNLConfigurationInfo                        CRITICALITY ignore  TYPE TNLConfigurationInfo                               PRESENCE optional   }|
    { ID id-TNLA-To-Add-List                            CRITICALITY ignore  TYPE TNLA-To-Add-List                                       PRESENCE optional }|
    { ID id-TNLA-To-Update-List                         CRITICALITY ignore  TYPE TNLA-To-Update-List                                    PRESENCE optional }|
    { ID id-TNLA-To-Remove-List                         CRITICALITY ignore  TYPE TNLA-To-Remove-List                                    PRESENCE optional },
    ...
}

InitiatingNodeType-EndcConfigUpdate::= CHOICE {
    init-eNB            ProtocolIE-Container    {{ENB-ENDCConfigUpdateIEs}},
    init-en-gNB         ProtocolIE-Container    {{En-gNB-ENDCConfigUpdateIEs}},
    ...
}

ENB-ENDCConfigUpdateIEs X2AP-PROTOCOL-IES ::= {
    { ID id-CellAssistanceInformation               CRITICALITY reject  TYPE CellAssistanceInformation                          PRESENCE optional }|
    { ID id-ServedEUTRAcellsENDCX2ManagementList        CRITICALITY reject  TYPE ServedEUTRAcellsENDCX2ManagementList           PRESENCE optional }|
    { ID id-ServedEUTRAcellsToModifyListENDCConfUpd CRITICALITY reject  TYPE ServedEUTRAcellsToModifyListENDCConfUpd        PRESENCE optional }|
    { ID id-ServedEUTRAcellsToDeleteListENDCConfUpd CRITICALITY reject  TYPE ServedEUTRAcellsToDeleteListENDCConfUpd        PRESENCE optional },
    ...
}

ServedEUTRAcellsToModifyListENDCConfUpd ::= SEQUENCE (SIZE (1.. maxCellineNB)) OF SEQUENCE {
    old-ECGI                                ECGI,
    servedEUTRACellInfo                 ServedCell-Information,
    nrNeighbourInfo                     NRNeighbour-Information     OPTIONAL,
    iE-Extensions                       ProtocolExtensionContainer { {ServedEUTRAcellsToModifyListENDCConfUpd-ExtIEs} } OPTIONAL,
    ...
}

ServedEUTRAcellsToModifyListENDCConfUpd-ExtIEs X2AP-PROTOCOL-EXTENSION ::= {
    ...
}

ServedEUTRAcellsToDeleteListENDCConfUpd ::= SEQUENCE (SIZE (1..maxCellineNB)) OF ECGI


En-gNB-ENDCConfigUpdateIEs X2AP-PROTOCOL-IES ::= {
    { ID id-ServedNRcellsENDCX2ManagementList       CRITICALITY reject  TYPE ServedNRcellsENDCX2ManagementList          PRESENCE optional }|
    { ID id-ServedNRcellsToModifyListENDCConfUpd        CRITICALITY reject  TYPE ServedNRcellsToModifyENDCConfUpdList       PRESENCE optional }|
    { ID id-ServedNRcellsToDeleteListENDCConfUpd        CRITICALITY reject  TYPE ServedNRcellsToDeleteENDCConfUpdList       PRESENCE optional },
    ...
}

ServedNRcellsToModifyENDCConfUpdList ::= SEQUENCE (SIZE (1..maxCellinengNB)) OF ServedNRCellsToModify-Item

ServedNRCellsToModify-Item::= SEQUENCE {
    old-nrcgi                       NRCGI,
    servedNRCellInformation         ServedNRCell-Information,
    nrNeighbourInformation          NRNeighbour-Information         OPTIONAL,
    nrDeactivationIndication            DeactivationIndication          OPTIONAL,
    iE-Extensions                   ProtocolExtensionContainer { {ServedNRCellsToModify-Item-ExtIEs} } OPTIONAL,
    ...
}

ServedNRCellsToModify-Item-ExtIEs X2AP-PROTOCOL-EXTENSION ::= {
    ...
}

ServedNRcellsToDeleteENDCConfUpdList ::= SEQUENCE (SIZE (1..maxCellinengNB)) OF NRCGI

-- **************************************************************
--
-- EN-DC CONFIGURATION UPDATE ACKNOWLEDGE
--
-- **************************************************************

ENDCConfigurationUpdateAcknowledge ::= SEQUENCE {
    protocolIEs     ProtocolIE-Container    {{ENDCConfigurationUpdateAcknowledge-IEs}},
    ...
}

ENDCConfigurationUpdateAcknowledge-IEs X2AP-PROTOCOL-IES ::= {
    { ID id-RespondingNodeType-EndcConfigUpdate         CRITICALITY reject  TYPE RespondingNodeType-EndcConfigUpdate            PRESENCE mandatory}|
    { ID id-InterfaceInstanceIndication                 CRITICALITY reject  TYPE InterfaceInstanceIndication                        PRESENCE optional }|
    { ID id-CriticalityDiagnostics                      CRITICALITY ignore  TYPE CriticalityDiagnostics PRESENCE optional }|
    { ID id-TNLConfigurationInfo                        CRITICALITY ignore  TYPE TNLConfigurationInfo                               PRESENCE optional }|
    { ID id-TNLA-Setup-List                             CRITICALITY ignore  TYPE TNLA-Setup-List                                            PRESENCE optional }|
    { ID id-TNLA-Failed-To-Setup-List                   CRITICALITY ignore  TYPE TNLA-Failed-To-Setup-List                          PRESENCE optional },
    ...
}


RespondingNodeType-EndcConfigUpdate::= CHOICE {
    respond-eNB         ProtocolIE-Container    {{ENB-ENDCConfigUpdateAckIEs}},
    respond-en-gNB      ProtocolIE-Container    {{En-gNB-ENDCConfigUpdateAckIEs}},
    ...
}


ENB-ENDCConfigUpdateAckIEs X2AP-PROTOCOL-IES ::= {
    ...
}

En-gNB-ENDCConfigUpdateAckIEs X2AP-PROTOCOL-IES ::= {
    { ID id-ServedNRcellsENDCX2ManagementList       CRITICALITY reject  TYPE ServedNRcellsENDCX2ManagementList      PRESENCE optional},
    ...
}


-- **************************************************************
--
-- EN-DC CONFIGURATION UPDATE FAILURE
--
-- **************************************************************

ENDCConfigurationUpdateFailure ::= SEQUENCE {
    protocolIEs     ProtocolIE-Container    {{ENDCConfigurationUpdateFailure-IEs}},
    ...
}

ENDCConfigurationUpdateFailure-IEs X2AP-PROTOCOL-IES ::= {
    { ID id-Cause                           CRITICALITY ignore  TYPE Cause                          PRESENCE mandatory}|
    { ID id-CriticalityDiagnostics          CRITICALITY ignore  TYPE CriticalityDiagnostics         PRESENCE optional }|
    { ID id-TimeToWait                      CRITICALITY ignore  TYPE TimeToWait                     PRESENCE optional }|
    { ID id-InterfaceInstanceIndication     CRITICALITY reject  TYPE InterfaceInstanceIndication        PRESENCE optional },
    ...
}


-- **************************************************************
--
-- EN-DC CELL ACTIVATION REQUEST
--
-- **************************************************************

ENDCCellActivationRequest ::= SEQUENCE {
    protocolIEs     ProtocolIE-Container    {{ENDCCellActivationRequest-IEs}},
    ...
}

ENDCCellActivationRequest-IEs X2AP-PROTOCOL-IES ::= {
    { ID id-ServedNRCellsToActivate         CRITICALITY reject  TYPE ServedNRCellsToActivate                PRESENCE mandatory}|
    { ID id-ActivationID                    CRITICALITY reject  TYPE ActivationID                       PRESENCE mandatory}|
    { ID id-InterfaceInstanceIndication CRITICALITY reject  TYPE InterfaceInstanceIndication            PRESENCE optional },
    ...
}

ServedNRCellsToActivate::= SEQUENCE (SIZE (1.. maxCellinengNB)) OF ServedNRCellsToActivate-Item

ServedNRCellsToActivate-Item::= SEQUENCE {
    nrCellID                        NRCGI,
    iE-Extensions                   ProtocolExtensionContainer { {ServedNRCellsToActivate-Item-ExtIEs} } OPTIONAL,
    ...
}

ServedNRCellsToActivate-Item-ExtIEs X2AP-PROTOCOL-EXTENSION ::= {
    ...
}

-- **************************************************************
--
-- EN-DC CELL ACTIVATION RESPONSE
--
-- **************************************************************

ENDCCellActivationResponse ::= SEQUENCE {
    protocolIEs     ProtocolIE-Container    {{ENDCCellActivationResponse-IEs}},
    ...
}

ENDCCellActivationResponse-IEs X2AP-PROTOCOL-IES ::= {
    { ID id-ActivatedNRCellList         CRITICALITY ignore  TYPE ActivatedNRCellList                PRESENCE mandatory}|
    { ID id-ActivationID                    CRITICALITY reject  TYPE ActivationID                       PRESENCE mandatory}|
    { ID id-CriticalityDiagnostics      CRITICALITY ignore  TYPE CriticalityDiagnostics         PRESENCE optional }|
    { ID id-InterfaceInstanceIndication CRITICALITY reject  TYPE InterfaceInstanceIndication        PRESENCE optional },
    ...
}

ActivatedNRCellList ::= SEQUENCE (SIZE (1.. maxCellinengNB)) OF ActivatedNRCellList-Item

ActivatedNRCellList-Item::= SEQUENCE {
    nrCellID                        NRCGI,
    iE-Extensions                       ProtocolExtensionContainer { {ActivatedNRCellList-Item-ExtIEs} } OPTIONAL,
    ...
}

ActivatedNRCellList-Item-ExtIEs X2AP-PROTOCOL-EXTENSION ::= {
    ...
}

--**************************************************************
--
-- EN-DC CELL ACTIVATION FAILURE
--
-- **************************************************************

ENDCCellActivationFailure ::= SEQUENCE {
    protocolIEs     ProtocolIE-Container    {{ENDCCellActivationFailure-IEs}},
    ...
}

ENDCCellActivationFailure-IEs X2AP-PROTOCOL-IES ::= {
    { ID id-ActivationID                        CRITICALITY reject  TYPE ActivationID                   PRESENCE mandatory }|
    { ID id-Cause                           CRITICALITY ignore  TYPE Cause                          PRESENCE mandatory }|
    { ID id-CriticalityDiagnostics          CRITICALITY ignore  TYPE CriticalityDiagnostics         PRESENCE optional }|
    { ID id-InterfaceInstanceIndication     CRITICALITY reject  TYPE InterfaceInstanceIndication        PRESENCE optional },
    ...
}

-- **************************************************************
--
-- EN-DC RESOURCE STATUS REQUEST
--
-- **************************************************************

ENDCResourceStatusRequest ::= SEQUENCE {
    protocolIEs     ProtocolIE-Container    {{ENDCResourceStatusRequest-IEs}},
    ...
}

ENDCResourceStatusRequest-IEs X2AP-PROTOCOL-IES ::= {
    { ID id-E-UTRAN-Node1-Measurement-ID            CRITICALITY reject  TYPE Measurement-ID-ENDC            PRESENCE mandatory  }|
    { ID id-E-UTRAN-Node2-Measurement-ID        CRITICALITY ignore  TYPE Measurement-ID-ENDC        PRESENCE conditional}| -- The IE shall be present if the Registration Request EN-DC IE is set to “Stop” or to “Add”
    { ID id-Registration-Request            CRITICALITY reject  TYPE Registration-Request-ENDC      PRESENCE mandatory  }|
    { ID id-ReportingPeriodicity            CRITICALITY ignore  TYPE ReportingPeriodicity-ENDC      PRESENCE optional   }|
    { ID id-ReportCharacteristics           CRITICALITY ignore  TYPE ReportCharacteristics-ENDC     PRESENCE conditional}| -- The IE shall be present if the Registration Request EN-DC IE is set to “Start”
    { ID id-CellToReport-NR-ENDC        CRITICALITY ignore  TYPE CellToReport-NR-ENDC-List          PRESENCE optional   } |
    { ID id-InterfaceInstanceIndication CRITICALITY reject  TYPE InterfaceInstanceIndication    PRESENCE optional   }|
    { ID id-CellToReport-E-UTRA-ENDC    CRITICALITY ignore  TYPE CellToReport-E-UTRA-ENDC-List      PRESENCE optional},
    ...
}

ReportingPeriodicity-ENDC ::= ENUMERATED {ms500, ms1000, ms2000, ms5000, ms10000, ...}

CellToReport-NR-ENDC-List   ::= SEQUENCE (SIZE (1..maxCellinengNB)) OF ProtocolIE-Single-Container { {CellToReport-NR-ENDC-ItemIEs} }

CellToReport-NR-ENDC-ItemIEs X2AP-PROTOCOL-IES ::= {
    { ID id-CellToReport-NR-ENDC-Item           CRITICALITY ignore  TYPE CellToReport-NR-ENDC-Item      PRESENCE mandatory}
}

CellToReport-NR-ENDC-Item               ::= SEQUENCE {
    nr-cell-ID                              NRCGI,
    ssbToReport-List                    SSBToReport-List                                    OPTIONAL,
    iE-Extensions                       ProtocolExtensionContainer { {CellToReport-NR-ENDC-Item-ExtIEs} } OPTIONAL,
    ...
}

CellToReport-NR-ENDC-Item-ExtIEs X2AP-PROTOCOL-EXTENSION ::= {
    ...
}

CellToReport-E-UTRA-ENDC-List       ::= SEQUENCE (SIZE (1..maxCellineNB)) OF ProtocolIE-Single-Container { {CellToReport-E-UTRA-ENDC-Item-IEs} }

CellToReport-E-UTRA-ENDC-Item-IEs X2AP-PROTOCOL-IES ::= {
    { ID id-CellToReport-E-UTRA-ENDC-Item   CRITICALITY ignore  TYPE CellToReport-E-UTRA-ENDC-Item  PRESENCE mandatory}
}

CellToReport-E-UTRA-ENDC-Item ::= SEQUENCE {
    e-utra-cell-ID                          ECGI,
    iE-Extensions                           ProtocolExtensionContainer { {CellToReport-E-UTRA-ENDC-Item-ExtIEs} } OPTIONAL,
    ...
}

CellToReport-E-UTRA-ENDC-Item-ExtIEs X2AP-PROTOCOL-EXTENSION ::= {
    ...
}

SSBToReport-List    ::= SEQUENCE (SIZE (1.. maxnoofSSBAreas)) OF SSBToReport-Item

SSBToReport-Item    ::= SEQUENCE {
    ssbIndex                            SSBIndex,
    iE-Extensions                       ProtocolExtensionContainer { {SSBToReport-Item-ExtIEs} } OPTIONAL,
    ...
}

SSBToReport-Item-ExtIEs X2AP-PROTOCOL-EXTENSION ::= {
    ...
}

-- **************************************************************
--
-- EN-DC RESOURCE STATUS RESPONSE
--
-- **************************************************************

ENDCResourceStatusResponse ::= SEQUENCE {
    protocolIEs     ProtocolIE-Container    {{ENDCResourceStatusResponse-IEs}},
    ...
}

ENDCResourceStatusResponse-IEs X2AP-PROTOCOL-IES ::= {
    { ID id-E-UTRAN-Node1-Measurement-ID        CRITICALITY reject  TYPE Measurement-ID-ENDC            PRESENCE mandatory}|
    { ID id-E-UTRAN-Node2-Measurement-ID    CRITICALITY reject  TYPE Measurement-ID-ENDC            PRESENCE mandatory}|
    { ID id-CriticalityDiagnostics      CRITICALITY ignore  TYPE CriticalityDiagnostics         PRESENCE optional } |
    { ID id-InterfaceInstanceIndication CRITICALITY reject  TYPE InterfaceInstanceIndication    PRESENCE optional },
    ...
}

-- **************************************************************
--
-- EN-DC RESOURCE STATUS FAILURE
--
-- **************************************************************

ENDCResourceStatusFailure ::= SEQUENCE {
    protocolIEs     ProtocolIE-Container    {{ENDCResourceStatusFailure-IEs}},
    ...
}

ENDCResourceStatusFailure-IEs X2AP-PROTOCOL-IES ::= {
    { ID id-E-UTRAN-Node1-Measurement-ID        CRITICALITY reject  TYPE Measurement-ID-ENDC            PRESENCE mandatory}|
    { ID id-E-UTRAN-Node2-Measurement-ID    CRITICALITY reject  TYPE Measurement-ID-ENDC            PRESENCE mandatory}|
    { ID id-Cause                       CRITICALITY ignore  TYPE Cause                          PRESENCE mandatory}|
    { ID id-CriticalityDiagnostics      CRITICALITY ignore  TYPE CriticalityDiagnostics         PRESENCE optional }|
    { ID id-InterfaceInstanceIndication CRITICALITY reject  TYPE InterfaceInstanceIndication    PRESENCE optional },
    ...
}

-- **************************************************************
--
-- EN-DC RESOURCE STATUS UPDATE
--
-- **************************************************************

ENDCResourceStatusUpdate ::= SEQUENCE {
    protocolIEs     ProtocolIE-Container    {{ENDCResourceStatusUpdate-IEs}},
    ...
}

ENDCResourceStatusUpdate-IEs X2AP-PROTOCOL-IES ::= {
    { ID id-E-UTRAN-Node1-Measurement-ID                CRITICALITY reject  TYPE Measurement-ID-ENDC                            PRESENCE mandatory}|
    { ID id-E-UTRAN-Node2-Measurement-ID            CRITICALITY reject  TYPE Measurement-ID-ENDC                            PRESENCE mandatory}|
    { ID id-CellMeasurementResult-NR-ENDC       CRITICALITY ignore  TYPE CellMeasurementResult-NR-ENDC-List     PRESENCE optional }|
    { ID id-InterfaceInstanceIndication         CRITICALITY reject  TYPE InterfaceInstanceIndication                    PRESENCE optional }|
    { ID id-CellMeasurementResult-E-UTRA-ENDC   CRITICALITY ignore  TYPE CellMeasurementResult-E-UTRA-ENDC-List PRESENCE optional},
    ...
}

CellMeasurementResult-NR-ENDC-List ::= SEQUENCE (SIZE (1..maxCellinengNB)) OF ProtocolIE-Single-Container { {CellMeasurementResult-NR-ENDC-ItemIEs} }

CellMeasurementResult-NR-ENDC-ItemIEs X2AP-PROTOCOL-IES ::= {
    { ID id-CellMeasurementResult-NR-ENDC-Item  CRITICALITY ignore  TYPE CellMeasurementResult-NR-ENDC-Item PRESENCE mandatory}
}

CellMeasurementResult-NR-ENDC-Item ::= SEQUENCE {
    nr-cell-ID                          NRCGI,
    nr-radioResourceStatus              NRRadioResourceStatus                               OPTIONAL,
    tnlCapacityIndicator                TNLCapacityIndicator                                OPTIONAL,
    nr-compositeAvailableCapacityGroup  NRCompositeAvailableCapacityGroup                   OPTIONAL,
    numberofActiveUEs                   INTEGER (0..16777215, ...)                          OPTIONAL,
    iE-Extensions                       ProtocolExtensionContainer { {CellMeasurementResult-NR-ENDC-Item-ExtIEs} }  OPTIONAL,
    ...
}

CellMeasurementResult-NR-ENDC-Item-ExtIEs X2AP-PROTOCOL-EXTENSION ::= {
    ...
}

CellMeasurementResult-E-UTRA-ENDC-List ::= SEQUENCE (SIZE (1..maxCellineNB))
                                                        OF ProtocolIE-Single-Container { {CellMeasurementResult-E-UTRA-ENDC-ItemIEs} }

CellMeasurementResult-E-UTRA-ENDC-ItemIEs X2AP-PROTOCOL-IES ::= {
    { ID id-CellMeasurementResult-E-UTRA-ENDC-Item  CRITICALITY ignore  TYPE CellMeasurementResult-E-UTRA-ENDC-Item PRESENCE mandatory}
}

CellMeasurementResult-E-UTRA-ENDC-Item ::= SEQUENCE {
    e-utra-cell-ID              ECGI,
    hWLoadIndicator             HWLoadIndicator     OPTIONAL,
    s1TNLLoadIndicator          S1TNLLoadIndicator  OPTIONAL,
    radioResourceStatus         RadioResourceStatus OPTIONAL,
    compositeAvailableCapacityGroup CompositeAvailableCapacityGroup OPTIONAL,
    iE-Extensions               ProtocolExtensionContainer { {CellMeasurementResult-E-UTRA-ENDC-Item-ExtIEs} }  OPTIONAL,
    ...
}

CellMeasurementResult-E-UTRA-ENDC-Item-ExtIEs X2AP-PROTOCOL-EXTENSION ::= {
    ...
}

-- **************************************************************
--
-- SECONDARY RAT DATA USAGE REPORT
--
-- **************************************************************

SecondaryRATDataUsageReport ::= SEQUENCE {
    protocolIEs     ProtocolIE-Container        {{SecondaryRATDataUsageReport-IEs}},
    ...
}

SecondaryRATDataUsageReport-IEs X2AP-PROTOCOL-IES ::= {
    { ID id-MeNB-UE-X2AP-ID                     CRITICALITY reject  TYPE UE-X2AP-ID                             PRESENCE mandatory}|
    { ID id-SgNB-UE-X2AP-ID                     CRITICALITY reject  TYPE SgNB-UE-X2AP-ID                            PRESENCE mandatory}|
    { ID id-SecondaryRATUsageReportList         CRITICALITY reject  TYPE SecondaryRATUsageReportList            PRESENCE mandatory}|
    { ID id-MeNB-UE-X2AP-ID-Extension           CRITICALITY reject  TYPE UE-X2AP-ID-Extension                   PRESENCE optional},
    ...
}

-- **************************************************************
--
-- SGNB ACTIVITY NOTIFICATION
--
-- **************************************************************

SgNBActivityNotification ::= SEQUENCE {
    protocolIEs     ProtocolIE-Container        {{SgNBActivityNotification-IEs}},
    ...
}

SgNBActivityNotification-IEs X2AP-PROTOCOL-IES ::= {
    { ID id-MeNB-UE-X2AP-ID                     CRITICALITY reject  TYPE UE-X2AP-ID                             PRESENCE mandatory}|
    { ID id-SgNB-UE-X2AP-ID                     CRITICALITY reject  TYPE SgNB-UE-X2AP-ID                            PRESENCE mandatory}|
    { ID id-UEContextLevelUserPlaneActivity     CRITICALITY ignore  TYPE UserPlaneTrafficActivityReport     PRESENCE optional}|
    { ID id-ERABActivityNotifyItemList          CRITICALITY ignore  TYPE ERABActivityNotifyItemList         PRESENCE optional}|
    { ID id-MeNB-UE-X2AP-ID-Extension           CRITICALITY reject  TYPE UE-X2AP-ID-Extension                   PRESENCE optional},
    ...
}

-- **************************************************************
--
-- EN-DC PARTIAL RESET REQUIRED
--
-- **************************************************************

ENDCPartialResetRequired ::= SEQUENCE {
    protocolIEs     ProtocolIE-Container    {{ENDCPartialResetRequired-IEs}},
    ...
}

ENDCPartialResetRequired-IEs X2AP-PROTOCOL-IES ::= {
    { ID id-UEs-ToBeReset               CRITICALITY reject  TYPE UEsToBeResetList                   PRESENCE mandatory}|
    { ID id-Cause                       CRITICALITY ignore  TYPE Cause                              PRESENCE mandatory}|
    { ID id-InterfaceInstanceIndication CRITICALITY reject  TYPE InterfaceInstanceIndication            PRESENCE optional},
    ...
}

-- **************************************************************
--
-- EN-DC PARTIAL RESET CONFIRM
--
-- **************************************************************

ENDCPartialResetConfirm ::= SEQUENCE {
    protocolIEs     ProtocolIE-Container    {{ENDCPartialResetConfirm-IEs}},
    ...
}

ENDCPartialResetConfirm-IEs X2AP-PROTOCOL-IES ::= {
    { ID id-UEs-Admitted-ToBeReset              CRITICALITY reject  TYPE UEsToBeResetList                   PRESENCE mandatory}|
    { ID id-InterfaceInstanceIndication         CRITICALITY reject  TYPE InterfaceInstanceIndication        PRESENCE optional},
    ...
}

-- **************************************************************
--
-- E-UTRA - NR CELL RESOURCE COORDINATION REQUEST
--
-- **************************************************************

EUTRANRCellResourceCoordinationRequest ::= SEQUENCE {
    protocolIEs     ProtocolIE-Container        {{EUTRANRCellResourceCoordinationRequest-IEs}},
    ...
}

EUTRANRCellResourceCoordinationRequest-IEs X2AP-PROTOCOL-IES ::= {
    { ID id-InitiatingNodeType-EutranrCellResourceCoordination  CRITICALITY reject  TYPE InitiatingNodeType-EutranrCellResourceCoordination         PRESENCE mandatory}|
    { ID id-InterfaceInstanceIndication                         CRITICALITY reject  TYPE InterfaceInstanceIndication                                        PRESENCE optional },
    ...
}

InitiatingNodeType-EutranrCellResourceCoordination ::= CHOICE {
    initiate-eNB            ProtocolIE-Container    {{ENB-EUTRA-NRCellResourceCoordinationReqIEs}},
    initiate-en-gNB         ProtocolIE-Container    {{En-gNB-EUTRA-NRCellResourceCoordinationReqIEs}},
    ...
}


ENB-EUTRA-NRCellResourceCoordinationReqIEs X2AP-PROTOCOL-IES ::= {
    { ID id-DataTrafficResourceIndication           CRITICALITY reject  TYPE DataTrafficResourceIndication                  PRESENCE mandatory}|
    { ID id-SpectrumSharingGroupID                  CRITICALITY reject  TYPE SpectrumSharingGroupID                         PRESENCE mandatory}|
    { ID id-ListofEUTRACellsinEUTRACoordinationReq  CRITICALITY reject  TYPE ListofEUTRACellsinEUTRACoordinationReq     PRESENCE mandatory},
    ...
}


En-gNB-EUTRA-NRCellResourceCoordinationReqIEs X2AP-PROTOCOL-IES ::= {
    { ID id-DataTrafficResourceIndication           CRITICALITY reject  TYPE DataTrafficResourceIndication              PRESENCE mandatory}|
    { ID id-ListofEUTRACellsinNRCoordinationReq     CRITICALITY reject  TYPE ListofEUTRACellsinNRCoordinationReq        PRESENCE mandatory }|
    { ID id-SpectrumSharingGroupID                  CRITICALITY reject  TYPE SpectrumSharingGroupID                     PRESENCE mandatory}|
    { ID id-ListofNRCellsinNRCoordinationReq        CRITICALITY reject  TYPE ListofNRCellsinNRCoordinationReq           PRESENCE mandatory},
    ...
}


ListofEUTRACellsinEUTRACoordinationReq ::= SEQUENCE (SIZE (0..maxCellineNB)) OF ECGI
ListofEUTRACellsinNRCoordinationReq ::= SEQUENCE (SIZE (1..maxCellineNB)) OF ECGI
ListofNRCellsinNRCoordinationReq ::= SEQUENCE (SIZE (0..maxnoNRcellsSpectrumSharingWithE-UTRA)) OF NRCGI

-- **************************************************************
--
-- E-UTRA - NR CELL RESOURCE COORDINATION RESPONSE
--
-- **************************************************************

EUTRANRCellResourceCoordinationResponse ::= SEQUENCE {
    protocolIEs     ProtocolIE-Container        {{EUTRANRCellResourceCoordinationResponse-IEs}},
    ...
}

EUTRANRCellResourceCoordinationResponse-IEs X2AP-PROTOCOL-IES ::= {
    { ID id-RespondingNodeType-EutranrCellResourceCoordination      CRITICALITY reject  TYPE RespondingNodeType-EutranrCellResourceCoordination         PRESENCE mandatory}|
    { ID id-InterfaceInstanceIndication CRITICALITY reject  TYPE InterfaceInstanceIndication    PRESENCE optional },
    ...
}

RespondingNodeType-EutranrCellResourceCoordination ::= CHOICE {
    respond-eNB         ProtocolIE-Container    {{ENB-EUTRA-NRCellResourceCoordinationReqAckIEs}},
    respond-en-gNB      ProtocolIE-Container    {{En-gNB-EUTRA-NRCellResourceCoordinationReqAckIEs}},
    ...
}


ENB-EUTRA-NRCellResourceCoordinationReqAckIEs X2AP-PROTOCOL-IES ::= {
    { ID id-DataTrafficResourceIndication               CRITICALITY reject  TYPE DataTrafficResourceIndication              PRESENCE mandatory}|
    { ID id-SpectrumSharingGroupID                      CRITICALITY reject  TYPE SpectrumSharingGroupID                         PRESENCE mandatory}|
    { ID id-ListofEUTRACellsinEUTRACoordinationResp     CRITICALITY reject  TYPE ListofEUTRACellsinEUTRACoordinationResp    PRESENCE mandatory},
    ...
}


En-gNB-EUTRA-NRCellResourceCoordinationReqAckIEs X2AP-PROTOCOL-IES ::= {
    { ID id-DataTrafficResourceIndication       CRITICALITY reject  TYPE DataTrafficResourceIndication          PRESENCE mandatory}|
    { ID id-SpectrumSharingGroupID              CRITICALITY reject  TYPE SpectrumSharingGroupID                     PRESENCE mandatory}|
    { ID id-ListofNRCellsinNRCoordinationResp   CRITICALITY reject  TYPE ListofNRCellsinNRCoordinationResp      PRESENCE mandatory},


    ...
}

ListofEUTRACellsinEUTRACoordinationResp ::= SEQUENCE (SIZE (0..maxCellineNB)) OF ECGI
ListofNRCellsinNRCoordinationResp ::= SEQUENCE (SIZE (0..maxnoNRcellsSpectrumSharingWithE-UTRA)) OF NRCGI

-- **************************************************************
--
-- EN-DC X2 REMOVAL REQUEST
--
-- **************************************************************

ENDCX2RemovalRequest ::= SEQUENCE {
    protocolIEs     ProtocolIE-Container    {{ENDCX2RemovalRequest-IEs}},
    ...
}

ENDCX2RemovalRequest-IEs X2AP-PROTOCOL-IES ::= {
    { ID id-InitiatingNodeType-EndcX2Removal            CRITICALITY reject  TYPE InitiatingNodeType-EndcX2Removal       PRESENCE mandatory}|
    { ID id-InterfaceInstanceIndication                 CRITICALITY reject  TYPE InterfaceInstanceIndication                PRESENCE optional },
    ...
}

InitiatingNodeType-EndcX2Removal ::= CHOICE {
    init-eNB                ProtocolIE-Container    {{ENB-ENDCX2RemovalReqIEs}},
    init-en-gNB         ProtocolIE-Container    {{En-gNB-ENDCX2RemovalReqIEs}},
    ...
}

ENB-ENDCX2RemovalReqIEs X2AP-PROTOCOL-IES ::= {
    { ID id-GlobalENB-ID                                CRITICALITY reject  TYPE GlobalENB-ID                                       PRESENCE mandatory},
    ...
}

En-gNB-ENDCX2RemovalReqIEs X2AP-PROTOCOL-IES ::= {
    { ID id-Globalen-gNB-ID                         CRITICALITY reject  TYPE GlobalGNB-ID                                       PRESENCE mandatory},
    ...
}

-- **************************************************************
--
-- EN-DC X2 REMOVAL RESPONSE
--
-- **************************************************************

ENDCX2RemovalResponse ::= SEQUENCE {
    protocolIEs     ProtocolIE-Container    {{ENDCX2RemovalResponse-IEs}},
    ...
}

ENDCX2RemovalResponse-IEs X2AP-PROTOCOL-IES ::= {
    { ID id-RespondingNodeType-EndcX2Removal        CRITICALITY reject  TYPE RespondingNodeType-EndcX2Removal       PRESENCE mandatory}|
    { ID id-InterfaceInstanceIndication             CRITICALITY reject  TYPE InterfaceInstanceIndication                PRESENCE optional },
    ...
}

RespondingNodeType-EndcX2Removal ::= CHOICE {
    respond-eNB         ProtocolIE-Container    {{ENB-ENDCX2RemovalReqAckIEs}},
    respond-en-gNB      ProtocolIE-Container    {{En-gNB-ENDCX2RemovalReqAckIEs}},
    ...
}

ENB-ENDCX2RemovalReqAckIEs X2AP-PROTOCOL-IES ::= {
    { ID id-GlobalENB-ID                                CRITICALITY reject  TYPE GlobalENB-ID                                       PRESENCE mandatory},
    ...
}

En-gNB-ENDCX2RemovalReqAckIEs X2AP-PROTOCOL-IES ::= {
    { ID id-Globalen-gNB-ID                         CRITICALITY reject  TYPE GlobalGNB-ID                                       PRESENCE mandatory},
    ...
}

-- **************************************************************
--
-- EN-DC X2 REMOVAL FAILURE
--
-- **************************************************************

ENDCX2RemovalFailure ::= SEQUENCE {
    protocolIEs     ProtocolIE-Container    {{ENDCX2RemovalFailure-IEs}},
    ...
}

ENDCX2RemovalFailure-IEs X2AP-PROTOCOL-IES ::= {
    { ID id-Cause                           CRITICALITY ignore      TYPE Cause                              PRESENCE mandatory} |
    { ID id-CriticalityDiagnostics          CRITICALITY ignore      TYPE CriticalityDiagnostics             PRESENCE optional }|
    { ID id-InterfaceInstanceIndication     CRITICALITY reject      TYPE InterfaceInstanceIndication        PRESENCE optional },
    ...
}

-- **************************************************************
--
-- DATA FORWARDING ADDRESS INDICATION
--
-- **************************************************************

DataForwardingAddressIndication ::= SEQUENCE {
    protocolIEs     ProtocolIE-Container    {{DataForwardingAddressIndication-IEs}},
    ...
}

DataForwardingAddressIndication-IEs X2AP-PROTOCOL-IES ::= {
    { ID id-New-eNB-UE-X2AP-ID                  CRITICALITY ignore  TYPE UE-X2AP-ID                                 PRESENCE mandatory}|
    { ID id-New-eNB-UE-X2AP-ID-Extension        CRITICALITY ignore  TYPE UE-X2AP-ID-Extension                       PRESENCE optional }|
    { ID id-Old-eNB-UE-X2AP-ID                  CRITICALITY ignore  TYPE UE-X2AP-ID                                 PRESENCE mandatory}|
    { ID id-Old-eNB-UE-X2AP-ID-Extension        CRITICALITY ignore  TYPE UE-X2AP-ID-Extension                       PRESENCE optional }|
    { ID id-E-RABs-DataForwardingAddress-List   CRITICALITY ignore  TYPE E-RABs-DataForwardingAddress-List      PRESENCE mandatory}|
    { ID id-CHO-DC-Indicator                    CRITICALITY reject  TYPE CHO-DC-Indicator                           PRESENCE optional}|
    { ID id-CHO-DC-EarlyDataForwarding          CRITICALITY ignore  TYPE CHO-DC-EarlyDataForwarding             PRESENCE optional}|
    { ID id-SgNB-UE-X2AP-ID                     CRITICALITY ignore  TYPE SgNB-UE-X2AP-ID                            PRESENCE optional}|
    { ID id-CPCinformation-NOTIFY               CRITICALITY reject  TYPE CPCinformation-NOTIFY                      PRESENCE optional},
    ...
}

E-RABs-DataForwardingAddress-List ::= SEQUENCE (SIZE(1..maxnoofBearers)) OF ProtocolIE-Single-Container { {E-RABs-DataForwardingAddress-ItemIEs} }

E-RABs-DataForwardingAddress-ItemIEs    X2AP-PROTOCOL-IES ::= {
    { ID id-E-RABs-DataForwardingAddress-Item   CRITICALITY ignore  TYPE E-RABs-DataForwardingAddress-Item  PRESENCE mandatory},
    ...
}

E-RABs-DataForwardingAddress-Item ::= SEQUENCE {
    e-RAB-ID                        E-RAB-ID,
    dl-GTPtunnelEndpoint            GTPtunnelEndpoint,
    iE-Extensions                   ProtocolExtensionContainer { {E-RABs-DataForwardingAddress-ItemExtIEs} } OPTIONAL,
    ...
}

E-RABs-DataForwardingAddress-ItemExtIEs X2AP-PROTOCOL-EXTENSION ::= {
    ...
}

-- **************************************************************
--
-- GNB STATUS INDICATION
--
-- **************************************************************


GNBStatusIndication ::= SEQUENCE {
    protocolIEs         ProtocolIE-Container    { { GNBStatusIndicationIEs} },
    ...
}

GNBStatusIndicationIEs X2AP-PROTOCOL-IES ::= {
    { ID id-GNBOverloadInformation          CRITICALITY ignore  TYPE GNBOverloadInformation         PRESENCE mandatory}|
    { ID id-InterfaceInstanceIndication     CRITICALITY reject  TYPE InterfaceInstanceIndication        PRESENCE optional },
    ...
}

-- **************************************************************
--
-- EN-DC CONFIGURATION TRANSFER
--
-- **************************************************************

ENDCConfigurationTransfer ::= SEQUENCE {
    protocolIEs     ProtocolIE-Container    {{ENDCConfigurationTransfer-IEs}},
    ...
}

ENDCConfigurationTransfer-IEs X2AP-PROTOCOL-IES ::= {
    { ID id-endcSONConfigurationTransfer    CRITICALITY ignore  TYPE EndcSONConfigurationTransfer           PRESENCE optional}|
    { ID id-InterfaceInstanceIndication     CRITICALITY reject  TYPE InterfaceInstanceIndication                PRESENCE optional },
    ...
}

-- **************************************************************
--
-- TRACE START
--
-- **************************************************************

TraceStart ::= SEQUENCE {
    protocolIEs     ProtocolIE-Container        { {TraceStartIEs} },
    ...
}

TraceStartIEs X2AP-PROTOCOL-IES ::= {
    { ID id-MeNB-UE-X2AP-ID             CRITICALITY reject  TYPE UE-X2AP-ID                     PRESENCE mandatory  }|
    { ID id-SgNB-UE-X2AP-ID             CRITICALITY reject  TYPE SgNB-UE-X2AP-ID                    PRESENCE mandatory  }|
    { ID id-TraceActivation             CRITICALITY ignore  TYPE TraceActivation                    PRESENCE mandatory  }|
    { ID id-MeNB-UE-X2AP-ID-Extension   CRITICALITY reject      TYPE UE-X2AP-ID-Extension           PRESENCE optional},
    ...
}

-- **************************************************************
--
-- DEACTIVATE TRACE
--
-- **************************************************************

DeactivateTrace ::= SEQUENCE {
    protocolIEs     ProtocolIE-Container        { {DeactivateTraceIEs} },
    ...
}

DeactivateTraceIEs X2AP-PROTOCOL-IES ::= {
    { ID id-MeNB-UE-X2AP-ID             CRITICALITY reject  TYPE UE-X2AP-ID                     PRESENCE mandatory  }|
    { ID id-SgNB-UE-X2AP-ID             CRITICALITY reject  TYPE SgNB-UE-X2AP-ID                    PRESENCE mandatory  }|
    { ID id-EUTRANTraceID               CRITICALITY ignore  TYPE EUTRANTraceID                  PRESENCE mandatory  }|
    { ID id-MeNB-UE-X2AP-ID-Extension       CRITICALITY reject  TYPE UE-X2AP-ID-Extension           PRESENCE optional},
    ...
}

-- **************************************************************
--
-- CELL TRAFFIC TRACE
--
-- **************************************************************

CellTrafficTrace ::= SEQUENCE {
    protocolIEs     ProtocolIE-Container        { {CellTrafficTraceIEs} },
    ...
}

CellTrafficTraceIEs X2AP-PROTOCOL-IES ::= {
    { ID id-MeNB-UE-X2AP-ID                 CRITICALITY reject  TYPE UE-X2AP-ID                         PRESENCE mandatory  }|
    { ID id-SgNB-UE-X2AP-ID                 CRITICALITY reject  TYPE SgNB-UE-X2AP-ID                    PRESENCE mandatory  }|
    { ID id-EUTRANTraceID                   CRITICALITY ignore  TYPE EUTRANTraceID                      PRESENCE mandatory  }|
    { ID id-TraceCollectionEntityIPAddress  CRITICALITY ignore  TYPE TraceCollectionEntityIPAddress PRESENCE mandatory  }|
    { ID id-PrivacyIndicator                CRITICALITY ignore  TYPE PrivacyIndicator                   PRESENCE optional   }|
    { ID id-MeNB-UE-X2AP-ID-Extension       CRITICALITY reject  TYPE UE-X2AP-ID-Extension               PRESENCE optional},
    ...
}

-- **************************************************************
--
-- F1-C TRAFFIC TRANSFER
--
-- **************************************************************

F1CTrafficTransfer ::= SEQUENCE {
    protocolIEs     ProtocolIE-Container        {{ F1CTrafficTransfer-IEs}},
    ...
}

F1CTrafficTransfer-IEs X2AP-PROTOCOL-IES ::= {
    { ID id-MeNB-UE-X2AP-ID                     CRITICALITY reject  TYPE UE-X2AP-ID                     PRESENCE mandatory}|
    { ID id-SgNB-UE-X2AP-ID                     CRITICALITY reject  TYPE SgNB-UE-X2AP-ID                PRESENCE mandatory}|
    { ID id-F1CTrafficContainer                 CRITICALITY reject  TYPE F1CTrafficContainer            PRESENCE mandatory}|
    { ID id-MeNB-UE-X2AP-ID-Extension           CRITICALITY reject  TYPE UE-X2AP-ID-Extension           PRESENCE optional},
    ...
}

-- **************************************************************
--
-- UE RADIO CAPABILITY ID MAPPING REQUEST
--
-- **************************************************************

UERadioCapabilityIDMappingRequest::= SEQUENCE {
    protocolIEs         ProtocolIE-Container       { { UERadioCapabilityIDMappingRequestIEs} },
    ...
}

UERadioCapabilityIDMappingRequestIEs X2AP-PROTOCOL-IES ::= {
    { ID id-UERadioCapabilityID     CRITICALITY reject  TYPE UERadioCapabilityID        PRESENCE mandatory  },
    ...
}

-- **************************************************************
--
-- UE RADIO CAPABILITY ID MAPPING RESPONSE
--
-- **************************************************************

UERadioCapabilityIDMappingResponse ::= SEQUENCE {
    protocolIEs         ProtocolIE-Container       { { UERadioCapabilityIDMappingResponseIEs} },
    ...
}

UERadioCapabilityIDMappingResponseIEs X2AP-PROTOCOL-IES ::= {
    { ID id-UERadioCapabilityID             CRITICALITY reject  TYPE UERadioCapabilityID            PRESENCE mandatory }|
    { ID id-UERadioCapability               CRITICALITY ignore  TYPE UERadioCapability              PRESENCE mandatory }|
    { ID id-CriticalityDiagnostics          CRITICALITY ignore  TYPE CriticalityDiagnostics         PRESENCE optional  },
    ...
}


-- **************************************************************
--
-- CONDITIONAL PSCELL CHANGE CANCEL
--
-- **************************************************************

CPC-cancel ::= SEQUENCE {
    protocolIEs     ProtocolIE-Container        {{CPC-cancel-IEs}},
    ...
}

CPC-cancel-IEs X2AP-PROTOCOL-IES ::= {
    { ID id-MeNB-UE-X2AP-ID                     CRITICALITY reject  TYPE UE-X2AP-ID                     PRESENCE mandatory}|
    { ID id-SgNB-UE-X2AP-ID                     CRITICALITY reject  TYPE SgNB-UE-X2AP-ID                PRESENCE mandatory}|
    { ID id-MeNB-UE-X2AP-ID-Extension           CRITICALITY reject  TYPE UE-X2AP-ID-Extension           PRESENCE optional}|
    { ID id-Cause                               CRITICALITY ignore  TYPE Cause                          PRESENCE optional}|
    { ID id-Target-SgNB-ID                      CRITICALITY reject  TYPE GlobalGNB-ID                   PRESENCE mandatory},
    ...
}


-- **************************************************************
--
-- RACH INDICATION
--
-- **************************************************************

RachIndication ::= SEQUENCE {
    protocolIEs         ProtocolIE-Container    {{ RachIndication-IEs}},
    ...
}

RachIndication-IEs X2AP-PROTOCOL-IES ::= {
    { ID id-RaReportIndicationList              CRITICALITY reject      TYPE RaReportIndicationList                         PRESENCE mandatory },
    ...
}

END
