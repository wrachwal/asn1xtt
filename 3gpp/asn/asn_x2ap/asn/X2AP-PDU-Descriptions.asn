-- ASN1START
-- **************************************************************
--
-- Elementary Procedure definitions
--
-- **************************************************************

X2AP-PDU-Descriptions {
itu-t (0) identified-organization (4) etsi (0) mobileDomain (0)
eps-Access (21) modules (3) x2ap (2) version1 (1) x2ap-PDU-Descriptions (0) }

DEFINITIONS AUTOMATIC TAGS ::=

BEGIN

-- **************************************************************
--
-- IE parameter types from other modules.
--
-- **************************************************************

IMPORTS
    Criticality,
    ProcedureCode

FROM X2AP-CommonDataTypes

    CellActivationRequest,
    CellActivationResponse,
    CellActivationFailure,
    ENBConfigurationUpdate,
    ENBConfigurationUpdateAcknowledge,
    ENBConfigurationUpdateFailure,
    ErrorIndication,
    HandoverCancel,
    HandoverReport,
    HandoverPreparationFailure,
    HandoverRequest,
    HandoverRequestAcknowledge,
    LoadInformation,
    PrivateMessage,
    ResetRequest,
    ResetResponse,
    ResourceStatusFailure,
    ResourceStatusRequest,
    ResourceStatusResponse,
    ResourceStatusUpdate,
    RLFIndication,
    SNStatusTransfer,
    UEContextRelease,
    X2SetupFailure,
    X2SetupRequest,
    X2SetupResponse,
    MobilityChangeRequest,
    MobilityChangeAcknowledge,
    MobilityChangeFailure,
    X2Release,
    X2APMessageTransfer,
    SeNBAdditionRequest,
    SeNBAdditionRequestAcknowledge,
    SeNBAdditionRequestReject,
    SeNBReconfigurationComplete,
    SeNBModificationRequest,
    SeNBModificationRequestAcknowledge,
    SeNBModificationRequestReject,
    SeNBModificationRequired,
    SeNBModificationConfirm,
    SeNBModificationRefuse,
    SeNBReleaseRequest,
    SeNBReleaseRequired,
    SeNBReleaseConfirm,
    SeNBCounterCheckRequest,
    X2RemovalFailure,
    X2RemovalRequest,
    X2RemovalResponse,
    RetrieveUEContextRequest,
    RetrieveUEContextResponse,
    RetrieveUEContextFailure,
    SgNBAdditionRequest,
    SgNBAdditionRequestAcknowledge,
    SgNBAdditionRequestReject,
    SgNBReconfigurationComplete,
    SgNBModificationRequest,
    SgNBModificationRequestAcknowledge,
    SgNBModificationRequestReject,
    SgNBModificationRequired,
    SgNBModificationConfirm,
    SgNBModificationRefuse,
    SgNBReleaseRequest,
    SgNBReleaseRequestAcknowledge,
    SgNBReleaseRequestReject,
    SgNBReleaseRequired,
    SgNBReleaseConfirm,
    SgNBCounterCheckRequest,
    SgNBChangeRequired,
    SgNBChangeConfirm,
    SgNBChangeRefuse,
    RRCTransfer,
    ENDCX2SetupRequest,
    ENDCX2SetupResponse,
    ENDCX2SetupFailure,
    ENDCConfigurationUpdate,
    ENDCConfigurationUpdateAcknowledge,
    ENDCConfigurationUpdateFailure,
    SecondaryRATDataUsageReport,
    ENDCCellActivationRequest,
    ENDCCellActivationResponse,
    ENDCCellActivationFailure,
    ENDCPartialResetRequired,
    ENDCPartialResetConfirm,
    EUTRANRCellResourceCoordinationRequest,
    EUTRANRCellResourceCoordinationResponse,
    SgNBActivityNotification,
    ENDCX2RemovalRequest,
    ENDCX2RemovalResponse,
    ENDCX2RemovalFailure,
    DataForwardingAddressIndication,
    GNBStatusIndication,
    ENDCConfigurationTransfer,
    DeactivateTrace,
    TraceStart,
    HandoverSuccess,
    EarlyStatusTransfer,
    ConditionalHandoverCancel,
    ENDCResourceStatusRequest,
    ENDCResourceStatusResponse,
    ENDCResourceStatusFailure,
    ENDCResourceStatusUpdate,
    CellTrafficTrace,
    F1CTrafficTransfer,
    UERadioCapabilityIDMappingRequest,
    UERadioCapabilityIDMappingResponse,
    AccessAndMobilityIndication,
    CPC-cancel,
    RachIndication





FROM X2AP-PDU-Contents

    id-cellActivation,
    id-eNBConfigurationUpdate,
    id-errorIndication,
    id-handoverCancel,
    id-handoverReport,
    id-handoverPreparation,

    id-loadIndication,
    id-privateMessage,
    id-reset,

    id-resourceStatusReporting,
    id-resourceStatusReportingInitiation,
    id-rLFIndication,
    id-snStatusTransfer,
    id-uEContextRelease,
    id-x2Setup,
    id-mobilitySettingsChange,
    id-x2Release,
    id-x2APMessageTransfer,
    id-seNBAdditionPreparation,
    id-seNBReconfigurationCompletion,
    id-meNBinitiatedSeNBModificationPreparation,
    id-seNBinitiatedSeNBModification,
    id-meNBinitiatedSeNBRelease,
    id-seNBinitiatedSeNBRelease,
    id-seNBCounterCheck,
    id-x2Removal,
    id-retrieveUEContext,
    id-sgNBAdditionPreparation,
    id-sgNBReconfigurationCompletion,
    id-meNBinitiatedSgNBModificationPreparation,
    id-sgNBinitiatedSgNBModification,
    id-meNBinitiatedSgNBRelease,
    id-sgNBinitiatedSgNBRelease,
    id-sgNBChange,
    id-sgNBCounterCheck,
    id-rRCTransfer,
    id-endcX2Setup,
    id-endcConfigurationUpdate,
    id-secondaryRATDataUsageReport,
    id-endcCellActivation,
    id-endcPartialReset,
    id-eUTRANRCellResourceCoordination,
    id-SgNBActivityNotification,
    id-endcX2Removal,
    id-dataForwardingAddressIndication,
    id-gNBStatusIndication,
    id-endcConfigurationTransfer,
    id-deactivateTrace,
    id-traceStart,
    id-handoverSuccess,
    id-earlyStatusTransfer,
    id-conditionalHandoverCancel,
    id-endcresourceStatusReporting,
    id-endcresourceStatusReportingInitiation,
    id-cellTrafficTrace,
    id-f1CTrafficTransfer,
    id-UERadioCapabilityIDMapping,
    id-accessAndMobilityIndication,
    id-CPC-cancel,
    id-rachIndication




FROM X2AP-Constants;

-- **************************************************************
--
-- Interface Elementary Procedure Class
--
-- **************************************************************

X2AP-ELEMENTARY-PROCEDURE ::= CLASS {
    &InitiatingMessage              ,
    &SuccessfulOutcome              OPTIONAL,
    &UnsuccessfulOutcome                OPTIONAL,
    &procedureCode          ProcedureCode   UNIQUE,
    &criticality            Criticality     DEFAULT ignore
}
WITH SYNTAX {
    INITIATING MESSAGE      &InitiatingMessage
    [SUCCESSFUL OUTCOME     &SuccessfulOutcome]
    [UNSUCCESSFUL OUTCOME       &UnsuccessfulOutcome]
    PROCEDURE CODE          &procedureCode
    [CRITICALITY            &criticality]
}

-- **************************************************************
--
-- Interface PDU Definition
--
-- **************************************************************

X2AP-PDU ::= CHOICE {
    initiatingMessage   InitiatingMessage,
    successfulOutcome   SuccessfulOutcome,
    unsuccessfulOutcome UnsuccessfulOutcome,
    ...
}

InitiatingMessage ::= SEQUENCE {
    procedureCode   X2AP-ELEMENTARY-PROCEDURE.&procedureCode        ({X2AP-ELEMENTARY-PROCEDURES}),
    criticality     X2AP-ELEMENTARY-PROCEDURE.&criticality          ({X2AP-ELEMENTARY-PROCEDURES}{@procedureCode}),
    value           X2AP-ELEMENTARY-PROCEDURE.&InitiatingMessage    ({X2AP-ELEMENTARY-PROCEDURES}{@procedureCode})
}

SuccessfulOutcome ::= SEQUENCE {
    procedureCode   X2AP-ELEMENTARY-PROCEDURE.&procedureCode        ({X2AP-ELEMENTARY-PROCEDURES}),
    criticality     X2AP-ELEMENTARY-PROCEDURE.&criticality          ({X2AP-ELEMENTARY-PROCEDURES}{@procedureCode}),
    value           X2AP-ELEMENTARY-PROCEDURE.&SuccessfulOutcome    ({X2AP-ELEMENTARY-PROCEDURES}{@procedureCode})
}

UnsuccessfulOutcome ::= SEQUENCE {
    procedureCode   X2AP-ELEMENTARY-PROCEDURE.&procedureCode        ({X2AP-ELEMENTARY-PROCEDURES}),
    criticality     X2AP-ELEMENTARY-PROCEDURE.&criticality          ({X2AP-ELEMENTARY-PROCEDURES}{@procedureCode}),
    value           X2AP-ELEMENTARY-PROCEDURE.&UnsuccessfulOutcome  ({X2AP-ELEMENTARY-PROCEDURES}{@procedureCode})
}

-- **************************************************************
--
-- Interface Elementary Procedure List
--
-- **************************************************************

X2AP-ELEMENTARY-PROCEDURES X2AP-ELEMENTARY-PROCEDURE ::= {
    X2AP-ELEMENTARY-PROCEDURES-CLASS-1          |
    X2AP-ELEMENTARY-PROCEDURES-CLASS-2          ,
    ...
}

X2AP-ELEMENTARY-PROCEDURES-CLASS-1 X2AP-ELEMENTARY-PROCEDURE ::= {
    handoverPreparation                                     |
    reset                                                   |
    x2Setup                                                 |
    resourceStatusReportingInitiation                       |
    eNBConfigurationUpdate                                  |
    mobilitySettingsChange                                  |
    cellActivation                                          |
    seNBAdditionPreparation                                 |
    meNBinitiatedSeNBModificationPreparation                |
    seNBinitiatedSeNBModification                           |
    seNBinitiatedSeNBRelease                                |
    x2Removal                                               |
    retrieveUEContext                                       |
    sgNBAdditionPreparation                                 |
    meNBinitiatedSgNBModificationPreparation                |
    sgNBinitiatedSgNBModification                           |
    meNBinitiatedSgNBRelease                                |
    sgNBinitiatedSgNBRelease                                |
    sgNBChange                                              |
    endcX2Setup                                             |
    endcConfigurationUpdate                                 |
    endcCellActivation                                      |
    endcPartialReset                                        |
    eUTRANRCellResourceCoordination                         |
    endcX2Removal                                           |
    endcresourceStatusReportingInitiation                   |
    uERadioCapabilityIDMapping                              ,
    ...
}

X2AP-ELEMENTARY-PROCEDURES-CLASS-2 X2AP-ELEMENTARY-PROCEDURE ::= {
    snStatusTransfer                        |
    uEContextRelease                        |
    handoverCancel                          |
    errorIndication                         |
    resourceStatusReporting                 |
    loadIndication                          |
    privateMessage                          |
    rLFIndication                           |
    handoverReport                          |
    x2Release                               |
    x2APMessageTransfer                     |
    seNBReconfigurationCompletion           |
    meNBinitiatedSeNBRelease                |
    seNBCounterCheck                        |
    sgNBReconfigurationCompletion           |
    sgNBCounterCheck                        |
    rRCTransfer                             |
    secondaryRATDataUsageReport             |
    sgNBActivityNotification                |
    dataForwardingAddressIndication         |
    gNBStatusIndication                     |
    endcConfigurationTransfer               |
    deactivateTrace                         |
    traceStart                              |
    handoverSuccess                         |
    earlyStatusTransfer                     |
    conditionalHandoverCancel               |
    endcresourceStatusReporting             |
    cellTrafficTrace                        |
    f1CTrafficTransfer                      |
    accessAndMobilityIndication             |
    cPC-cancel                              |
    rachIndication                          ,
    ...

}

-- **************************************************************
--
-- Interface Elementary Procedures
--
-- **************************************************************

handoverPreparation X2AP-ELEMENTARY-PROCEDURE ::= {
    INITIATING MESSAGE      HandoverRequest
    SUCCESSFUL OUTCOME      HandoverRequestAcknowledge
    UNSUCCESSFUL OUTCOME    HandoverPreparationFailure
    PROCEDURE CODE          id-handoverPreparation
    CRITICALITY             reject
}

snStatusTransfer X2AP-ELEMENTARY-PROCEDURE ::= {
    INITIATING MESSAGE      SNStatusTransfer
    PROCEDURE CODE          id-snStatusTransfer
    CRITICALITY             ignore
}

uEContextRelease X2AP-ELEMENTARY-PROCEDURE ::= {
    INITIATING MESSAGE      UEContextRelease
    PROCEDURE CODE          id-uEContextRelease
    CRITICALITY             ignore
}


handoverCancel X2AP-ELEMENTARY-PROCEDURE ::= {
    INITIATING MESSAGE      HandoverCancel
    PROCEDURE CODE          id-handoverCancel
    CRITICALITY             ignore
}

handoverReport X2AP-ELEMENTARY-PROCEDURE ::= {
    INITIATING MESSAGE      HandoverReport
    PROCEDURE CODE          id-handoverReport
    CRITICALITY             ignore
}

errorIndication X2AP-ELEMENTARY-PROCEDURE ::= {
    INITIATING MESSAGE      ErrorIndication
    PROCEDURE CODE          id-errorIndication
    CRITICALITY             ignore
}

reset   X2AP-ELEMENTARY-PROCEDURE ::= {
    INITIATING MESSAGE      ResetRequest
    SUCCESSFUL OUTCOME      ResetResponse
    PROCEDURE CODE          id-reset
    CRITICALITY             reject
}

x2Setup X2AP-ELEMENTARY-PROCEDURE ::= {
    INITIATING MESSAGE      X2SetupRequest
    SUCCESSFUL OUTCOME      X2SetupResponse
    UNSUCCESSFUL OUTCOME    X2SetupFailure
    PROCEDURE CODE          id-x2Setup
    CRITICALITY             reject
}


loadIndication X2AP-ELEMENTARY-PROCEDURE ::= {
    INITIATING MESSAGE      LoadInformation
    PROCEDURE CODE          id-loadIndication
    CRITICALITY             ignore
}

eNBConfigurationUpdate      X2AP-ELEMENTARY-PROCEDURE ::= {
    INITIATING MESSAGE      ENBConfigurationUpdate
    SUCCESSFUL OUTCOME      ENBConfigurationUpdateAcknowledge
    UNSUCCESSFUL OUTCOME    ENBConfigurationUpdateFailure
    PROCEDURE CODE          id-eNBConfigurationUpdate
    CRITICALITY             reject
}

resourceStatusReportingInitiation   X2AP-ELEMENTARY-PROCEDURE ::= {
    INITIATING MESSAGE              ResourceStatusRequest
    SUCCESSFUL OUTCOME              ResourceStatusResponse
    UNSUCCESSFUL OUTCOME            ResourceStatusFailure
    PROCEDURE CODE                  id-resourceStatusReportingInitiation
    CRITICALITY                     reject
}

resourceStatusReporting X2AP-ELEMENTARY-PROCEDURE ::= {
    INITIATING MESSAGE      ResourceStatusUpdate
    PROCEDURE CODE          id-resourceStatusReporting
    CRITICALITY             ignore
}

rLFIndication X2AP-ELEMENTARY-PROCEDURE ::= {
    INITIATING MESSAGE      RLFIndication
    PROCEDURE CODE          id-rLFIndication
    CRITICALITY             ignore
}

privateMessage          X2AP-ELEMENTARY-PROCEDURE ::= {
    INITIATING MESSAGE      PrivateMessage
    PROCEDURE CODE          id-privateMessage
    CRITICALITY             ignore
}

mobilitySettingsChange  X2AP-ELEMENTARY-PROCEDURE ::= {
    INITIATING MESSAGE      MobilityChangeRequest
    SUCCESSFUL OUTCOME      MobilityChangeAcknowledge
    UNSUCCESSFUL OUTCOME    MobilityChangeFailure
    PROCEDURE CODE          id-mobilitySettingsChange
    CRITICALITY             reject
}

cellActivation  X2AP-ELEMENTARY-PROCEDURE ::= {
    INITIATING MESSAGE      CellActivationRequest
    SUCCESSFUL OUTCOME      CellActivationResponse
    UNSUCCESSFUL OUTCOME    CellActivationFailure
    PROCEDURE CODE          id-cellActivation
    CRITICALITY             reject
}

x2Release X2AP-ELEMENTARY-PROCEDURE ::= {
    INITIATING MESSAGE      X2Release
    PROCEDURE CODE          id-x2Release
    CRITICALITY             reject
}

x2APMessageTransfer X2AP-ELEMENTARY-PROCEDURE ::= {
    INITIATING MESSAGE      X2APMessageTransfer
    PROCEDURE CODE          id-x2APMessageTransfer
    CRITICALITY             reject
}

seNBAdditionPreparation X2AP-ELEMENTARY-PROCEDURE ::= {
    INITIATING MESSAGE      SeNBAdditionRequest
    SUCCESSFUL OUTCOME      SeNBAdditionRequestAcknowledge
    UNSUCCESSFUL OUTCOME    SeNBAdditionRequestReject
    PROCEDURE CODE          id-seNBAdditionPreparation
    CRITICALITY             reject
}

seNBReconfigurationCompletion   X2AP-ELEMENTARY-PROCEDURE ::= {
    INITIATING MESSAGE      SeNBReconfigurationComplete
    PROCEDURE CODE          id-seNBReconfigurationCompletion
    CRITICALITY             ignore
}

meNBinitiatedSeNBModificationPreparation    X2AP-ELEMENTARY-PROCEDURE ::= {
    INITIATING MESSAGE      SeNBModificationRequest
    SUCCESSFUL OUTCOME      SeNBModificationRequestAcknowledge
    UNSUCCESSFUL OUTCOME    SeNBModificationRequestReject
    PROCEDURE CODE          id-meNBinitiatedSeNBModificationPreparation
    CRITICALITY             reject
}

seNBinitiatedSeNBModification   X2AP-ELEMENTARY-PROCEDURE ::= {
    INITIATING MESSAGE      SeNBModificationRequired
    SUCCESSFUL OUTCOME      SeNBModificationConfirm
    UNSUCCESSFUL OUTCOME    SeNBModificationRefuse
    PROCEDURE CODE          id-seNBinitiatedSeNBModification
    CRITICALITY             reject
}

meNBinitiatedSeNBRelease    X2AP-ELEMENTARY-PROCEDURE ::= {
    INITIATING MESSAGE      SeNBReleaseRequest
    PROCEDURE CODE          id-meNBinitiatedSeNBRelease
    CRITICALITY             ignore
}

seNBinitiatedSeNBRelease    X2AP-ELEMENTARY-PROCEDURE ::= {
    INITIATING MESSAGE      SeNBReleaseRequired
    SUCCESSFUL OUTCOME      SeNBReleaseConfirm
    PROCEDURE CODE          id-seNBinitiatedSeNBRelease
    CRITICALITY             reject
}

seNBCounterCheck    X2AP-ELEMENTARY-PROCEDURE ::= {
    INITIATING MESSAGE      SeNBCounterCheckRequest
    PROCEDURE CODE          id-seNBCounterCheck
    CRITICALITY             reject
}

x2Removal   X2AP-ELEMENTARY-PROCEDURE ::= {
    INITIATING MESSAGE      X2RemovalRequest
    SUCCESSFUL OUTCOME      X2RemovalResponse
    UNSUCCESSFUL OUTCOME    X2RemovalFailure
    PROCEDURE CODE          id-x2Removal
    CRITICALITY             reject
}

retrieveUEContext   X2AP-ELEMENTARY-PROCEDURE ::= {
    INITIATING MESSAGE      RetrieveUEContextRequest
    SUCCESSFUL OUTCOME      RetrieveUEContextResponse
    UNSUCCESSFUL OUTCOME    RetrieveUEContextFailure
    PROCEDURE CODE          id-retrieveUEContext
    CRITICALITY             reject
}

sgNBAdditionPreparation     X2AP-ELEMENTARY-PROCEDURE ::= {
    INITIATING MESSAGE      SgNBAdditionRequest
    SUCCESSFUL OUTCOME      SgNBAdditionRequestAcknowledge
    UNSUCCESSFUL OUTCOME    SgNBAdditionRequestReject
    PROCEDURE CODE          id-sgNBAdditionPreparation
    CRITICALITY             reject
}

sgNBReconfigurationCompletion   X2AP-ELEMENTARY-PROCEDURE ::= {
    INITIATING MESSAGE      SgNBReconfigurationComplete
    PROCEDURE CODE          id-sgNBReconfigurationCompletion
    CRITICALITY             ignore
}

meNBinitiatedSgNBModificationPreparation    X2AP-ELEMENTARY-PROCEDURE ::= {
    INITIATING MESSAGE      SgNBModificationRequest
    SUCCESSFUL OUTCOME      SgNBModificationRequestAcknowledge
    UNSUCCESSFUL OUTCOME    SgNBModificationRequestReject
    PROCEDURE CODE          id-meNBinitiatedSgNBModificationPreparation
    CRITICALITY             reject
}

sgNBinitiatedSgNBModification       X2AP-ELEMENTARY-PROCEDURE ::= {
    INITIATING MESSAGE      SgNBModificationRequired
    SUCCESSFUL OUTCOME      SgNBModificationConfirm
    UNSUCCESSFUL OUTCOME    SgNBModificationRefuse
    PROCEDURE CODE          id-sgNBinitiatedSgNBModification
    CRITICALITY             reject
}

meNBinitiatedSgNBRelease    X2AP-ELEMENTARY-PROCEDURE ::= {
    INITIATING MESSAGE      SgNBReleaseRequest
    SUCCESSFUL OUTCOME      SgNBReleaseRequestAcknowledge
    UNSUCCESSFUL OUTCOME    SgNBReleaseRequestReject
    PROCEDURE CODE          id-meNBinitiatedSgNBRelease
    CRITICALITY             ignore
}

sgNBinitiatedSgNBRelease    X2AP-ELEMENTARY-PROCEDURE ::= {
    INITIATING MESSAGE      SgNBReleaseRequired
    SUCCESSFUL OUTCOME      SgNBReleaseConfirm
    PROCEDURE CODE          id-sgNBinitiatedSgNBRelease
    CRITICALITY             reject
}

sgNBCounterCheck    X2AP-ELEMENTARY-PROCEDURE ::= {
    INITIATING MESSAGE      SgNBCounterCheckRequest
    PROCEDURE CODE          id-sgNBCounterCheck
    CRITICALITY             reject
}

sgNBChange  X2AP-ELEMENTARY-PROCEDURE ::= {
    INITIATING MESSAGE      SgNBChangeRequired
    SUCCESSFUL OUTCOME      SgNBChangeConfirm
    UNSUCCESSFUL OUTCOME    SgNBChangeRefuse
    PROCEDURE CODE          id-sgNBChange
    CRITICALITY             reject
}

rRCTransfer X2AP-ELEMENTARY-PROCEDURE ::= {
    INITIATING MESSAGE      RRCTransfer
    PROCEDURE CODE          id-rRCTransfer
    CRITICALITY             reject
}

endcX2Setup X2AP-ELEMENTARY-PROCEDURE ::= {
    INITIATING MESSAGE      ENDCX2SetupRequest
    SUCCESSFUL OUTCOME      ENDCX2SetupResponse
    UNSUCCESSFUL OUTCOME    ENDCX2SetupFailure
    PROCEDURE CODE          id-endcX2Setup
    CRITICALITY             reject
}


endcConfigurationUpdate     X2AP-ELEMENTARY-PROCEDURE ::= {
    INITIATING MESSAGE      ENDCConfigurationUpdate
    SUCCESSFUL OUTCOME      ENDCConfigurationUpdateAcknowledge
    UNSUCCESSFUL OUTCOME    ENDCConfigurationUpdateFailure
    PROCEDURE CODE          id-endcConfigurationUpdate
    CRITICALITY             reject
}

secondaryRATDataUsageReport X2AP-ELEMENTARY-PROCEDURE ::= {
    INITIATING MESSAGE      SecondaryRATDataUsageReport
    PROCEDURE CODE          id-secondaryRATDataUsageReport
    CRITICALITY             reject
}

endcCellActivation  X2AP-ELEMENTARY-PROCEDURE ::= {
    INITIATING MESSAGE      ENDCCellActivationRequest
    SUCCESSFUL OUTCOME      ENDCCellActivationResponse
    UNSUCCESSFUL OUTCOME    ENDCCellActivationFailure
    PROCEDURE CODE          id-endcCellActivation
    CRITICALITY             reject
}

endcPartialReset    X2AP-ELEMENTARY-PROCEDURE ::= {
    INITIATING MESSAGE      ENDCPartialResetRequired
    SUCCESSFUL OUTCOME      ENDCPartialResetConfirm
    PROCEDURE CODE          id-endcPartialReset
    CRITICALITY             reject
}

eUTRANRCellResourceCoordination X2AP-ELEMENTARY-PROCEDURE ::= {
    INITIATING MESSAGE      EUTRANRCellResourceCoordinationRequest
    SUCCESSFUL OUTCOME      EUTRANRCellResourceCoordinationResponse
    PROCEDURE CODE          id-eUTRANRCellResourceCoordination
    CRITICALITY             reject
}

sgNBActivityNotification    X2AP-ELEMENTARY-PROCEDURE ::= {
    INITIATING MESSAGE      SgNBActivityNotification
    PROCEDURE CODE          id-SgNBActivityNotification
    CRITICALITY             reject
}


endcX2Removal   X2AP-ELEMENTARY-PROCEDURE ::= {
    INITIATING MESSAGE      ENDCX2RemovalRequest
    SUCCESSFUL OUTCOME      ENDCX2RemovalResponse
    UNSUCCESSFUL OUTCOME    ENDCX2RemovalFailure
    PROCEDURE CODE          id-endcX2Removal
    CRITICALITY             reject
}

dataForwardingAddressIndication X2AP-ELEMENTARY-PROCEDURE ::= {
    INITIATING MESSAGE      DataForwardingAddressIndication
    PROCEDURE CODE          id-dataForwardingAddressIndication
    CRITICALITY             ignore
}

gNBStatusIndication     X2AP-ELEMENTARY-PROCEDURE ::= {
    INITIATING MESSAGE      GNBStatusIndication
    PROCEDURE CODE          id-gNBStatusIndication
    CRITICALITY             ignore
}

endcConfigurationTransfer   X2AP-ELEMENTARY-PROCEDURE ::= {
    INITIATING MESSAGE      ENDCConfigurationTransfer
    PROCEDURE CODE          id-endcConfigurationTransfer
    CRITICALITY             ignore
}

deactivateTrace X2AP-ELEMENTARY-PROCEDURE ::= {
    INITIATING MESSAGE      DeactivateTrace
    PROCEDURE CODE          id-deactivateTrace
    CRITICALITY             ignore
}

traceStart X2AP-ELEMENTARY-PROCEDURE ::= {
    INITIATING MESSAGE      TraceStart
    PROCEDURE CODE          id-traceStart
    CRITICALITY             ignore
}

handoverSuccess X2AP-ELEMENTARY-PROCEDURE ::= {
    INITIATING MESSAGE      HandoverSuccess
    PROCEDURE CODE          id-handoverSuccess
    CRITICALITY             ignore
}

earlyStatusTransfer     X2AP-ELEMENTARY-PROCEDURE ::= {
    INITIATING MESSAGE      EarlyStatusTransfer
    PROCEDURE CODE          id-earlyStatusTransfer
    CRITICALITY             ignore
}

conditionalHandoverCancel X2AP-ELEMENTARY-PROCEDURE ::= {
    INITIATING MESSAGE      ConditionalHandoverCancel
    PROCEDURE CODE          id-conditionalHandoverCancel
    CRITICALITY             ignore
}

endcresourceStatusReportingInitiation   X2AP-ELEMENTARY-PROCEDURE ::= {
    INITIATING MESSAGE      ENDCResourceStatusRequest
    SUCCESSFUL OUTCOME      ENDCResourceStatusResponse
    UNSUCCESSFUL OUTCOME    ENDCResourceStatusFailure
    PROCEDURE CODE          id-endcresourceStatusReportingInitiation
    CRITICALITY             reject
}

endcresourceStatusReporting     X2AP-ELEMENTARY-PROCEDURE ::= {
    INITIATING MESSAGE      ENDCResourceStatusUpdate
    PROCEDURE CODE          id-endcresourceStatusReporting
    CRITICALITY             ignore
}

cellTrafficTrace X2AP-ELEMENTARY-PROCEDURE ::= {
    INITIATING MESSAGE      CellTrafficTrace
    PROCEDURE CODE          id-cellTrafficTrace
    CRITICALITY             ignore
}

f1CTrafficTransfer          X2AP-ELEMENTARY-PROCEDURE ::= {
    INITIATING MESSAGE      F1CTrafficTransfer
    PROCEDURE CODE          id-f1CTrafficTransfer
    CRITICALITY             ignore
}

uERadioCapabilityIDMapping X2AP-ELEMENTARY-PROCEDURE ::= {
    INITIATING MESSAGE      UERadioCapabilityIDMappingRequest
    SUCCESSFUL OUTCOME      UERadioCapabilityIDMappingResponse
    PROCEDURE CODE          id-UERadioCapabilityIDMapping
    CRITICALITY             reject
}

accessAndMobilityIndication X2AP-ELEMENTARY-PROCEDURE ::={
    INITIATING MESSAGE      AccessAndMobilityIndication
    PROCEDURE CODE          id-accessAndMobilityIndication
    CRITICALITY                 ignore
}


cPC-cancel X2AP-ELEMENTARY-PROCEDURE ::= {
    INITIATING MESSAGE      CPC-cancel
    PROCEDURE CODE          id-CPC-cancel
    CRITICALITY             ignore
}


rachIndication X2AP-ELEMENTARY-PROCEDURE ::= {
    INITIATING MESSAGE      RachIndication
    PROCEDURE CODE          id-rachIndication
    CRITICALITY             ignore
}

END
