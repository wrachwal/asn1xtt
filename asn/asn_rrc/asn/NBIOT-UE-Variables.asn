NBIOT-UE-Variables DEFINITIONS AUTOMATIC TAGS ::=

BEGIN

IMPORTS
    VarShortMAC-Input,
    VarShortResumeMAC-Input-r13

FROM EUTRA-UE-Variables;

VarShortMAC-Input-NB-r13        ::=     VarShortMAC-Input

VarShortResumeMAC-Input-NB-r13  ::=     VarShortResumeMAC-Input-r13


END
